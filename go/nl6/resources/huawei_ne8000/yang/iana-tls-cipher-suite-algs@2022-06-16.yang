module iana-tls-cipher-suite-algs {
  yang-version 1.1;
  namespace "urn:ietf:params:xml:ns:yang:iana-tls-cipher-suite-algs";
  prefix tlscsa;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines identities for the Cipher Suite
     algorithms defined in the 'TLS Cipher Suites' sub-registry
     of the 'Transport Layer Security (TLS) Parameters' registry
     maintained by IANA.

     Copyright (c) 2022 IETF Trust and the persons identified as
     authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC FFFF
     (https://www.rfc-editor.org/info/rfcFFFF); see the RFC
     itself for full legal notices.";

  revision 2022-06-16 {
   description
      "Reflect contents of the public key algorithms registry
       on June 16, 2022.";
    reference
      "RFC FFFF: YANG Groupings for TLS Clients and TLS Servers";
  }

  // Typedefs

  typedef cipher-suite-algorithm-ref {
    type identityref {
      base "cipher-suite-alg-base";
    }
    description
      "A reference to a TLS cipher suite algorithm identifier.";
  }

  // Identities

  identity cipher-suite-alg-base {
    description
      "Base identity used to identify TLS cipher suites.";
  }

  identity tls-null-with-null-null {
    base cipher-suite-alg-base;
    status deprecated;
    description
      "TLS-NULL-WITH-NULL-NULL";
    reference
      "RFC 5246:
         The Transport Layer Security (TLS) Protocol Version 1.2";
  }

  identity tls-rsa-with-null-md5 {
    base cipher-suite-alg-base;
    status deprecated;
    description
      "TLS-RSA-WITH-NULL-MD5";
    reference
      "RFC 5246:
         The Transport Layer Security (TLS) Protocol Version 1.2";
  }

  identity tls-rsa-with-null-sha {
    base cipher-suite-alg-base;
    status deprecated;
    description
      "TLS-RSA-WITH-NULL-SHA";
    reference
      "RFC 5246:
         The Transport Layer Security (TLS) Protocol Version 1.2";
  }

  identity tls-rsa-export-with-rc4-40-md5 {
    base cipher-suite-alg-base;
    status deprecated;
    description
      "TLS-RSA-EXPORT-WITH-RC4-40-MD5";
    reference
      "RFC 4346:
         The TLS Protocol Version 1.1
       RFC 6347:
         Datagram Transport Layer Security version 1.2";
  }

  identity tls-rsa-with-rc4-128-md5 {
    base cipher-suite-alg-base;
    status deprecated;
    description
      "TLS-RSA-WITH-RC4-128-MD5";
    reference
      "RFC 5246:
         The Transport Layer Security (TLS) Protocol Version 1.2
       RFC 6347:
         Datagram Transport Layer Security version 1.2";
  }

  identity tls-rsa-with-rc4-128-sha {
    base cipher-suite-alg-base;
    status deprecated;
    description
      "TLS-RSA-WITH-RC4-128-SHA";
    reference
      "RFC 5246:
         The Transport Layer Security (TLS) Protocol Version 1.2
       RFC 6347:
         Datagram Transport Layer Security version 1.2";
  }
  identity tls-rsa-export-with-rc2-cbc-40-md5 {
    base cipher-suite-alg-base;
    status deprecated;
    description
      "TLS-RSA-EXPORT-WITH-RC2-CBC-40-MD5";
    reference
      "RFC 4346:
         The TLS Protocol Version 1.1";
  }

  identity tls-rsa-with-idea-cbc-sha {
    base cipher-suite-alg-base;
    status obsolete;
    description
      "TLS-RSA-WITH-IDEA-CBC-SHA";
    reference
      "RFC 5469:
         DES and IDEA Cipher Suites for
         Transport Layer Security (TLS)
       RFC 5469:
         DES and IDEA Cipher Suites for
         Transport Layer Security (TLS)";
  }

  identity tls-rsa-export-with-des40-cbc-sha {
    base cipher-suite-alg-base;
    status deprecated;
    description
      "TLS-RSA-EXPORT-WITH-DES40-CBC-SHA";
    reference
      "RFC 4346:
         The TLS Protocol Version 1.1";
  }

  identity tls-rsa-with-des-cbc-sha {
    base cipher-suite-alg-base;
    status obsolete;
    description
      "TLS-RSA-WITH-DES-CBC-SHA";
    reference
      "RFC 5469:
         DES and IDEA Cipher Suites for
         Transport Layer Security (TLS)
       RFC 5469:
         DES and IDEA Cipher Suites for
         Transport Layer Security (TLS)";
  }

  identity tls-rsa-with-3des-ede-cbc-sha {
    base cipher-suite-alg-base;
    status deprecated;
    description
      "TLS-RSA-WITH-3DES-EDE-CBC-SHA";
    reference
      "RFC 5246:
         The Transport Layer Security (TLS) Protocol Version 1.2";
  }

  identity tls-dh-dss-export-with-des40-cbc-sha {
    base cipher-suite-alg-base;
    status deprecated;
    description
      "TLS-DH-DSS-EXPORT-WITH-DES40-CBC-SHA";
    reference
      "RFC 4346:
         The TLS Protocol Version 1.1";
  }

  identity tls-dh-dss-with-des-cbc-sha {
    base cipher-suite-alg-base;
    status obsolete;
    description
      "TLS-DH-DSS-WITH-DES-CBC-SHA";
    reference
      "RFC 5469:
         DES and IDEA Cipher Suites for
         Transport Layer Security (TLS)
       RFC 5469:
         DES and IDEA Cipher Suites for
         Transport Layer Security (TLS)";
  }

  identity tls-dh-dss-with-3des-ede-cbc-sha {
    base cipher-suite-alg-base;
    status deprecated;
    description
      "TLS-DH-DSS-WITH-3DES-EDE-CBC-SHA";
    reference
      "RFC 5246:
         The Transport Layer Security (TLS) Protocol Version 1.2";
  }

  identity tls-dh-rsa-export-with-des40-cbc-sha {
    base cipher-suite-alg-base;
    status deprecated;
    description
      "TLS-DH-RSA-EXPORT-WITH-DES40-CBC-SHA";
    reference
      "RFC 4346:
         The TLS Protocol Version 1.1";
  }

  identity tls-dh-rsa-with-des-cbc-sha {
    base cipher-suite-alg-base;
    status obsolete;
    description
      "TLS-DH-RSA-WITH-DES-CBC-SHA";
    reference
      "RFC 5469:
         DES and IDEA Cipher Suites for
         Transport Layer Security (TLS)
       RFC 5469:
         DES and IDEA Cipher Suites for
         Transport Layer Security (TLS)";
  }

  identity tls-dh-rsa-with-3des-ede-cbc-sha {
    base cipher-suite-alg-base;
    status deprecated;
    description
      "TLS-DH-RSA-WITH-3DES-EDE-CBC-SHA";
    reference
      "RFC 5246:
         The Transport Layer Security (TLS) Protocol Version 1.2";
  }

  identity tls-dhe-dss-export-with-des40-cbc-sha {
    base cipher-suite-alg-base;
    status deprecated;
    description
      "TLS-DHE-DSS-EXPORT-WITH-DES40-CBC-SHA";
    reference
      "RFC 4346:
         The TLS Protocol Version 1.1";
  }

  identity tls-dhe-dss-with-des-cbc-sha {
    base cipher-suite-alg-base;
    status obsolete;
    description
      "TLS-DHE-DSS-WITH-DES-CBC-SHA";
    reference
      "RFC 5469:
         DES and IDEA Cipher Suites for
         Transport Layer Security (TLS)
       RFC 5469:
         DES and IDEA Cipher Suites for
         Transport Layer Security (TLS)";
  }

  identity tls-dhe-dss-with-3des-ede-cbc-sha {
    base cipher-suite-alg-base;
    status deprecated;
    description
      "TLS-DHE-DSS-WITH-3DES-EDE-CBC-SHA";
    reference
      "RFC 5246:
         The Transport Layer Security (TLS) Protocol Version 1.2";
  }

  identity tls-dhe-rsa-export-with-des40-cbc-sha {
    base cipher-suite-alg-base;
    status deprecated;
    description
      "TLS-DHE-RSA-EXPORT-WITH-DES40-CBC-SHA";
    reference
      "RFC 4346:
         The TLS Protocol Version 1.1";
  }

  identity tls-dhe-rsa-with-des-cbc-sha {
    base cipher-suite-alg-base;
    status obsolete;
    description
      "TLS-DHE-RSA-WITH-DES-CBC-SHA";
    reference
      "RFC 5469:
         DES and IDEA Cipher Suites for
         Transport Layer Security (TLS)
       RFC 5469:
         DES and IDEA Cipher Suites for
         Transport Layer Security (TLS)";
  }

  identity tls-dhe-rsa-with-3des-ede-cbc-sha {
    base cipher-suite-alg-base;
    status deprecated;
    description
      "TLS-DHE-RSA-WITH-3DES-EDE-CBC-SHA";
    reference
      "RFC 5246:
         The Transport Layer Security (TLS) Protocol Version 1.2";
  }

  identity tls-dh-anon-export-with-rc4-40-md5 {
    base cipher-suite-alg-base;
    status deprecated;
    description
      "TLS-DH-ANON-EXPORT-WITH-RC4-40-MD5";
    reference
      "RFC 4346:
         The TLS Protocol Version 1.1
       RFC 6347:
         Datagram Transport Layer Security version 1.2";
  }

  identity tls-dh-anon-with-rc4-128-md5 {
    base cipher-suite-alg-base;
    status deprecated;
    description
      "TLS-DH-ANON-WITH-RC4-128-MD5";
    reference
      "RFC 5246:
         The Transport Layer Security (TLS) Protocol Version 1.2
       RFC 6347:
         Datagram Transport Layer Security version 1.2";
  }

  identity tls-dh-anon-export-with-des40-cbc-sha {
    base cipher-suite-alg-base;
    status deprecated;
    description
      "TLS-DH-ANON-EXPORT-WITH-DES40-CBC-SHA";
    reference
      "RFC 4346:
         The TLS Protocol Version 1.1";
  }

  identity tls-dh-anon-with-des-cbc-sha {
    base cipher-suite-alg-base;
    status obsolete;
    description
      "TLS-DH-ANON-WITH-DES-CBC-SHA";
    reference
      "RFC 5469:
         DES and IDEA Cipher Suites for
         Transport Layer Security (TLS)
       RFC 5469:
         DES and IDEA Cipher Suites for
         Transport Layer Security (TLS)";
  }

  identity tls-dh-anon-with-3des-ede-cbc-sha {
    base cipher-suite-alg-base;
    status deprecated;
    description
      "TLS-DH-ANON-WITH-3DES-EDE-CBC-SHA";
    reference
      "RFC 5246:
         The Transport Layer Security (TLS) Protocol Version 1.2";
  }

  identity tls-krb5-with-des-cbc-sha {
    base cipher-suite-alg-base;
    status deprecated;
    description
      "TLS-KRB5-WITH-DES-CBC-SHA";
    reference
      "RFC 2712:
         Addition of Kerberos Cipher Suites to
         Transport Layer Security (TLS)";
  }

  identity tls-krb5-with-3des-ede-cbc-sha {
    base cipher-suite-alg-base;
    status deprecated;
    description
      "TLS-KRB5-WITH-3DES-EDE-CBC-SHA";
    reference
      "RFC 2712:
         Addition of Kerberos Cipher Suites to
         Transport Layer Security (TLS)";
  }

  identity tls-krb5-with-rc4-128-sha {
    base cipher-suite-alg-base;
    status deprecated;
    description
      "TLS-KRB5-WITH-RC4-128-SHA";
    reference
      "RFC 2712:
         Addition of Kerberos Cipher Suites to
         Transport Layer Security (TLS)
       RFC 6347:
         Datagram Transport Layer Security version 1.2";
  }

  identity tls-krb5-with-idea-cbc-sha {
    base cipher-suite-alg-base;
    status deprecated;
    description
      "TLS-KRB5-WITH-IDEA-CBC-SHA";
    reference
      "RFC 2712:
         Addition of Kerberos Cipher Suites to
         Transport Layer Security (TLS)";
  }

  identity tls-krb5-with-des-cbc-md5 {
    base cipher-suite-alg-base;
    status deprecated;
    description
      "TLS-KRB5-WITH-DES-CBC-MD5";
    reference
      "RFC 2712:
         Addition of Kerberos Cipher Suites to
         Transport Layer Security (TLS)";
  }

  identity tls-krb5-with-3des-ede-cbc-md5 {
    base cipher-suite-alg-base;
    status deprecated;
    description
      "TLS-KRB5-WITH-3DES-EDE-CBC-MD5";
    reference
      "RFC 2712:
         Addition of Kerberos Cipher Suites to
         Transport Layer Security (TLS)";
  }

  identity tls-krb5-with-rc4-128-md5 {
    base cipher-suite-alg-base;
    status deprecated;
    description
      "TLS-KRB5-WITH-RC4-128-MD5";
    reference
      "RFC 2712:
         Addition of Kerberos Cipher Suites to
         Transport Layer Security (TLS)
       RFC 6347:
         Datagram Transport Layer Security version 1.2";
  }

  identity tls-krb5-with-idea-cbc-md5 {
    base cipher-suite-alg-base;
    status deprecated;
    description
      "TLS-KRB5-WITH-IDEA-CBC-MD5";
    reference
      "RFC 2712:
         Addition of Kerberos Cipher Suites to
         Transport Layer Security (TLS)";
  }

  identity tls-krb5-export-with-des-cbc-40-sha {
    base cipher-suite-alg-base;
    status deprecated;
    description
      "TLS-KRB5-EXPORT-WITH-DES-CBC-40-SHA";
    reference
      "RFC 2712:
         Addition of Kerberos Cipher Suites to
         Transport Layer Security (TLS)";
  }

  identity tls-krb5-export-with-rc2-cbc-40-sha {
    base cipher-suite-alg-base;
    status deprecated;
    description
      "TLS-KRB5-EXPORT-WITH-RC2-CBC-40-SHA";
    reference
      "RFC 2712:
         Addition of Kerberos Cipher Suites to
         Transport Layer Security (TLS)";
  }

  identity tls-krb5-export-with-rc4-40-sha {
    base cipher-suite-alg-base;
    status deprecated;
    description
      "TLS-KRB5-EXPORT-WITH-RC4-40-SHA";
    reference
      "RFC 2712:
         Addition of Kerberos Cipher Suites to
         Transport Layer Security (TLS)
       RFC 6347:
         Datagram Transport Layer Security version 1.2";
  }

  identity tls-krb5-export-with-des-cbc-40-md5 {
    base cipher-suite-alg-base;
    status deprecated;
    description
      "TLS-KRB5-EXPORT-WITH-DES-CBC-40-MD5";
    reference
      "RFC 2712:
         Addition of Kerberos Cipher Suites to
         Transport Layer Security (TLS)";
  }

  identity tls-krb5-export-with-rc2-cbc-40-md5 {
    base cipher-suite-alg-base;
    status deprecated;
    description
      "TLS-KRB5-EXPORT-WITH-RC2-CBC-40-MD5";
    reference
      "RFC 2712:
         Addition of Kerberos Cipher Suites to
         Transport Layer Security (TLS)";
  }

  identity tls-krb5-export-with-rc4-40-md5 {
    base cipher-suite-alg-base;
    status deprecated;
    description
      "TLS-KRB5-EXPORT-WITH-RC4-40-MD5";
    reference
      "RFC 2712:
         Addition of Kerberos Cipher Suites to
         Transport Layer Security (TLS)
       RFC 6347:
         Datagram Transport Layer Security version 1.2";
  }

  identity tls-psk-with-null-sha {
    base cipher-suite-alg-base;
    status deprecated;
    description
      "TLS-PSK-WITH-NULL-SHA";
    reference
      "RFC 4785:
         Pre-Shared Key Cipher Suites with NULL Encryption for
         Transport Layer Security (TLS)";
  }

  identity tls-dhe-psk-with-null-sha {
    base cipher-suite-alg-base;
    status deprecated;
    description
      "TLS-DHE-PSK-WITH-NULL-SHA";
    reference
      "RFC 4785:
         Pre-Shared Key Cipher Suites with NULL Encryption for
         Transport Layer Security (TLS)";
  }

  identity tls-rsa-psk-with-null-sha {
    base cipher-suite-alg-base;
    status deprecated;
    description
      "TLS-RSA-PSK-WITH-NULL-SHA";
    reference
      "RFC 4785:
         Pre-Shared Key Cipher Suites with NULL Encryption for
         Transport Layer Security (TLS)";
  }

  identity tls-rsa-with-aes-128-cbc-sha {
    base cipher-suite-alg-base;
    status deprecated;
    description
      "TLS-RSA-WITH-AES-128-CBC-SHA";
    reference
      "RFC 5246:
         The Transport Layer Security (TLS) Protocol Version 1.2";
  }

  identity tls-dh-dss-with-aes-128-cbc-sha {
    base cipher-suite-alg-base;
    status deprecated;
    description
      "TLS-DH-DSS-WITH-AES-128-CBC-SHA";
    reference
      "RFC 5246:
         The Transport Layer Security (TLS) Protocol Version 1.2";
  }

  identity tls-dh-rsa-with-aes-128-cbc-sha {
    base cipher-suite-alg-base;
    status deprecated;
    description
      "TLS-DH-RSA-WITH-AES-128-CBC-SHA";
    reference
      "RFC 5246:
         The Transport Layer Security (TLS) Protocol Version 1.2";
  }

  identity tls-dhe-dss-with-aes-128-cbc-sha {
    base cipher-suite-alg-base;
    status deprecated;
    description
      "TLS-DHE-DSS-WITH-AES-128-CBC-SHA";
    reference
      "RFC 5246:
         The Transport Layer Security (TLS) Protocol Version 1.2";
  }

  identity tls-dhe-rsa-with-aes-128-cbc-sha {
    base cipher-suite-alg-base;
    status deprecated;
    description
      "TLS-DHE-RSA-WITH-AES-128-CBC-SHA";
    reference
      "RFC 5246:
         The Transport Layer Security (TLS) Protocol Version 1.2";
  }

  identity tls-dh-anon-with-aes-128-cbc-sha {
    base cipher-suite-alg-base;
    status deprecated;
    description
      "TLS-DH-ANON-WITH-AES-128-CBC-SHA";
    reference
      "RFC 5246:
         The Transport Layer Security (TLS) Protocol Version 1.2";
  }

  identity tls-rsa-with-aes-256-cbc-sha {
    base cipher-suite-alg-base;
    status deprecated;
    description
      "TLS-RSA-WITH-AES-256-CBC-SHA";
    reference
      "RFC 5246:
         The Transport Layer Security (TLS) Protocol Version 1.2";
  }

  identity tls-dh-dss-with-aes-256-cbc-sha {
    base cipher-suite-alg-base;
    status deprecated;
    description
      "TLS-DH-DSS-WITH-AES-256-CBC-SHA";
    reference
      "RFC 5246:
         The Transport Layer Security (TLS) Protocol Version 1.2";
  }

  identity tls-dh-rsa-with-aes-256-cbc-sha {
    base cipher-suite-alg-base;
    status deprecated;
    description
      "TLS-DH-RSA-WITH-AES-256-CBC-SHA";
    reference
      "RFC 5246:
         The Transport Layer Security (TLS) Protocol Version 1.2";
  }

  identity tls-dhe-dss-with-aes-256-cbc-sha {
    base cipher-suite-alg-base;
    status deprecated;
    description
      "TLS-DHE-DSS-WITH-AES-256-CBC-SHA";
    reference
      "RFC 5246:
         The Transport Layer Security (TLS) Protocol Version 1.2";
  }

  identity tls-dhe-rsa-with-aes-256-cbc-sha {
    base cipher-suite-alg-base;
    status deprecated;
    description
      "TLS-DHE-RSA-WITH-AES-256-CBC-SHA";
    reference
      "RFC 5246:
         The Transport Layer Security (TLS) Protocol Version 1.2";
  }

  identity tls-dh-anon-with-aes-256-cbc-sha {
    base cipher-suite-alg-base;
    status deprecated;
    description
      "TLS-DH-ANON-WITH-AES-256-CBC-SHA";
    reference
      "RFC 5246:
         The Transport Layer Security (TLS) Protocol Version 1.2";
  }

  identity tls-rsa-with-null-sha256 {
    base cipher-suite-alg-base;
    status deprecated;
    description
      "TLS-RSA-WITH-NULL-SHA256";
    reference
      "RFC 5246:
         The Transport Layer Security (TLS) Protocol Version 1.2";
  }
  identity tls-rsa-with-aes-128-cbc-sha256 {
    base cipher-suite-alg-base;
    status deprecated;
    description
      "TLS-RSA-WITH-AES-128-CBC-SHA256";
    reference
      "RFC 5246:
         The Transport Layer Security (TLS) Protocol Version 1.2";
  }

  identity tls-rsa-with-aes-256-cbc-sha256 {
    base cipher-suite-alg-base;
    status deprecated;
    description
      "TLS-RSA-WITH-AES-256-CBC-SHA256";
    reference
      "RFC 5246:
         The Transport Layer Security (TLS) Protocol Version 1.2";
  }

  identity tls-dh-dss-with-aes-128-cbc-sha256 {
    base cipher-suite-alg-base;
    status deprecated;
    description
      "TLS-DH-DSS-WITH-AES-128-CBC-SHA256";
    reference
      "RFC 5246:
         The Transport Layer Security (TLS) Protocol Version 1.2";
  }

  identity tls-dh-rsa-with-aes-128-cbc-sha256 {
    base cipher-suite-alg-base;
    status deprecated;
    description
      "TLS-DH-RSA-WITH-AES-128-CBC-SHA256";
    reference
      "RFC 5246:
         The Transport Layer Security (TLS) Protocol Version 1.2";
  }

  identity tls-dhe-dss-with-aes-128-cbc-sha256 {
    base cipher-suite-alg-base;
    status deprecated;
    description
      "TLS-DHE-DSS-WITH-AES-128-CBC-SHA256";
    reference
      "RFC 5246:
         The Transport Layer Security (TLS) Protocol Version 1.2";
  }

  identity tls-rsa-with-camellia-128-cbc-sha {
    base cipher-suite-alg-base;
    status deprecated;
    description
      "TLS-RSA-WITH-CAMELLIA-128-CBC-SHA";
    reference
      "RFC 5932:
         Camellia Cipher Suites for TLS";
  }

  identity tls-dh-dss-with-camellia-128-cbc-sha {
    base cipher-suite-alg-base;
    status deprecated;
    description
      "TLS-DH-DSS-WITH-CAMELLIA-128-CBC-SHA";
    reference
      "RFC 5932:
         Camellia Cipher Suites for TLS";
  }

  identity tls-dh-rsa-with-camellia-128-cbc-sha {
    base cipher-suite-alg-base;
    status deprecated;
    description
      "TLS-DH-RSA-WITH-CAMELLIA-128-CBC-SHA";
    reference
      "RFC 5932:
         Camellia Cipher Suites for TLS";
  }

  identity tls-dhe-dss-with-camellia-128-cbc-sha {
    base cipher-suite-alg-base;
    status deprecated;
    description
      "TLS-DHE-DSS-WITH-CAMELLIA-128-CBC-SHA";
    reference
      "RFC 5932:
         Camellia Cipher Suites for TLS";
  }

  identity tls-dhe-rsa-with-camellia-128-cbc-sha {
    base cipher-suite-alg-base;
    status deprecated;
    description
      "TLS-DHE-RSA-WITH-CAMELLIA-128-CBC-SHA";
    reference
      "RFC 5932:
         Camellia Cipher Suites for TLS";
  }

  identity tls-dh-anon-with-camellia-128-cbc-sha {
    base cipher-suite-alg-base;
    status deprecated;
    description
      "TLS-DH-ANON-WITH-CAMELLIA-128-CBC-SHA";
    reference
      "RFC 5932:
         Camellia Cipher Suites for TLS";
  }

  identity tls-dhe-rsa-with-aes-128-cbc-sha256 {
    base cipher-suite-alg-base;
    status deprecated;
    description
      "TLS-DHE-RSA-WITH-AES-128-CBC-SHA256";
    reference
      "RFC 5246:
         The Transport Layer Security (TLS) Protocol Version 1.2";
  }

  identity tls-dh-dss-with-aes-256-cbc-sha256 {
    base cipher-suite-alg-base;
    status deprecated;
    description
      "TLS-DH-DSS-WITH-AES-256-CBC-SHA256";
    reference
      "RFC 5246:
         The Transport Layer Security (TLS) Protocol Version 1.2";
  }

  identity tls-dh-rsa-with-aes-256-cbc-sha256 {
    base cipher-suite-alg-base;
    status deprecated;
    description
      "TLS-DH-RSA-WITH-AES-256-CBC-SHA256";
    reference
      "RFC 5246:
         The Transport Layer Security (TLS) Protocol Version 1.2";
  }

  identity tls-dhe-dss-with-aes-256-cbc-sha256 {
    base cipher-suite-alg-base;
    status deprecated;
    description
      "TLS-DHE-DSS-WITH-AES-256-CBC-SHA256";
    reference
      "RFC 5246:
         The Transport Layer Security (TLS) Protocol Version 1.2";
  }

  identity tls-dhe-rsa-with-aes-256-cbc-sha256 {
    base cipher-suite-alg-base;
    status deprecated;
    description
      "TLS-DHE-RSA-WITH-AES-256-CBC-SHA256";
    reference
      "RFC 5246:
         The Transport Layer Security (TLS) Protocol Version 1.2";
  }

  identity tls-dh-anon-with-aes-128-cbc-sha256 {
    base cipher-suite-alg-base;
    status deprecated;
    description
      "TLS-DH-ANON-WITH-AES-128-CBC-SHA256";
    reference
      "RFC 5246:
         The Transport Layer Security (TLS) Protocol Version 1.2";
  }

  identity tls-dh-anon-with-aes-256-cbc-sha256 {
    base cipher-suite-alg-base;
    status deprecated;
    description
      "TLS-DH-ANON-WITH-AES-256-CBC-SHA256";
    reference
      "RFC 5246:
         The Transport Layer Security (TLS) Protocol Version 1.2";
  }

  identity tls-rsa-with-camellia-256-cbc-sha {
    base cipher-suite-alg-base;
    status deprecated;
    description
      "TLS-RSA-WITH-CAMELLIA-256-CBC-SHA";
    reference
      "RFC 5932:
         Camellia Cipher Suites for TLS";
  }

  identity tls-dh-dss-with-camellia-256-cbc-sha {
    base cipher-suite-alg-base;
    status deprecated;
    description
      "TLS-DH-DSS-WITH-CAMELLIA-256-CBC-SHA";
    reference
      "RFC 5932:
         Camellia Cipher Suites for TLS";
  }

  identity tls-dh-rsa-with-camellia-256-cbc-sha {
    base cipher-suite-alg-base;
    status deprecated;
    description
      "TLS-DH-RSA-WITH-CAMELLIA-256-CBC-SHA";
    reference
      "RFC 5932:
         Camellia Cipher Suites for TLS";
  }

  identity tls-dhe-dss-with-camellia-256-cbc-sha {
    base cipher-suite-alg-base;
    status deprecated;
    description
      "TLS-DHE-DSS-WITH-CAMELLIA-256-CBC-SHA";
    reference
      "RFC 5932:
         Camellia Cipher Suites for TLS";
  }

  identity tls-dhe-rsa-with-camellia-256-cbc-sha {
    base cipher-suite-alg-base;
    status deprecated;
    description
      "TLS-DHE-RSA-WITH-CAMELLIA-256-CBC-SHA";
    reference
      "RFC 5932:
         Camellia Cipher Suites for TLS";
  }

  identity tls-dh-anon-with-camellia-256-cbc-sha {
    base cipher-suite-alg-base;
    status deprecated;
    description
      "TLS-DH-ANON-WITH-CAMELLIA-256-CBC-SHA";
    reference
      "RFC 5932:
         Camellia Cipher Suites for TLS";
  }

  identity tls-psk-with-rc4-128-sha {
    base cipher-suite-alg-base;
    status deprecated;
    description
      "TLS-PSK-WITH-RC4-128-SHA";
    reference
      "RFC 4279:
         Pre-Shared Key Ciphersuites for
         Transport Layer Security (TLS)
       RFC 6347:
         Datagram Transport Layer Security version 1.2";
  }

  identity tls-psk-with-3des-ede-cbc-sha {
    base cipher-suite-alg-base;
    status deprecated;
    description
      "TLS-PSK-WITH-3DES-EDE-CBC-SHA";
    reference
      "RFC 4279:
         Pre-Shared Key Ciphersuites for
         Transport Layer Security (TLS)";
  }

  identity tls-psk-with-aes-128-cbc-sha {
    base cipher-suite-alg-base;
    status deprecated;
    description
      "TLS-PSK-WITH-AES-128-CBC-SHA";
    reference
      "RFC 4279:
         Pre-Shared Key Ciphersuites for
         Transport Layer Security (TLS)";
  }

  identity tls-psk-with-aes-256-cbc-sha {
    base cipher-suite-alg-base;
    status deprecated;
    description
      "TLS-PSK-WITH-AES-256-CBC-SHA";
    reference
      "RFC 4279:
         Pre-Shared Key Ciphersuites for
         Transport Layer Security (TLS)";
  }

  identity tls-dhe-psk-with-rc4-128-sha {
    base cipher-suite-alg-base;
    status deprecated;
    description
      "TLS-DHE-PSK-WITH-RC4-128-SHA";
    reference
      "RFC 4279:
         Pre-Shared Key Ciphersuites for
         Transport Layer Security (TLS)
       RFC 6347:
         Datagram Transport Layer Security version 1.2";
  }

  identity tls-dhe-psk-with-3des-ede-cbc-sha {
    base cipher-suite-alg-base;
    status deprecated;
    description
      "TLS-DHE-PSK-WITH-3DES-EDE-CBC-SHA";
    reference
      "RFC 4279:
         Pre-Shared Key Ciphersuites for
         Transport Layer Security (TLS)";
  }

  identity tls-dhe-psk-with-aes-128-cbc-sha {
    base cipher-suite-alg-base;
    status deprecated;
    description
      "TLS-DHE-PSK-WITH-AES-128-CBC-SHA";
    reference
      "RFC 4279:
         Pre-Shared Key Ciphersuites for
         Transport Layer Security (TLS)";
  }

  identity tls-dhe-psk-with-aes-256-cbc-sha {
    base cipher-suite-alg-base;
    status deprecated;
    description
      "TLS-DHE-PSK-WITH-AES-256-CBC-SHA";
    reference
      "RFC 4279:
         Pre-Shared Key Ciphersuites for
         Transport Layer Security (TLS)";
  }

  identity tls-rsa-psk-with-rc4-128-sha {
    base cipher-suite-alg-base;
    status deprecated;
    description
      "TLS-RSA-PSK-WITH-RC4-128-SHA";
    reference
      "RFC 4279:
         Pre-Shared Key Ciphersuites for
         Transport Layer Security (TLS)
       RFC 6347:
         Datagram Transport Layer Security version 1.2";
  }

  identity tls-rsa-psk-with-3des-ede-cbc-sha {
    base cipher-suite-alg-base;
    status deprecated;
    description
      "TLS-RSA-PSK-WITH-3DES-EDE-CBC-SHA";
    reference
      "RFC 4279:
         Pre-Shared Key Ciphersuites for
         Transport Layer Security (TLS)";
  }

  identity tls-rsa-psk-with-aes-128-cbc-sha {
    base cipher-suite-alg-base;
    status deprecated;
    description
      "TLS-RSA-PSK-WITH-AES-128-CBC-SHA";
    reference
      "RFC 4279:
         Pre-Shared Key Ciphersuites for
         Transport Layer Security (TLS)";
  }

  identity tls-rsa-psk-with-aes-256-cbc-sha {
    base cipher-suite-alg-base;
    status deprecated;
    description
      "TLS-RSA-PSK-WITH-AES-256-CBC-SHA";
    reference
      "RFC 4279:
         Pre-Shared Key Ciphersuites for
         Transport Layer Security (TLS)";
  }

  identity tls-rsa-with-seed-cbc-sha {
    base cipher-suite-alg-base;
    status deprecated;
    description
      "TLS-RSA-WITH-SEED-CBC-SHA";
    reference
      "RFC 4162:
         Addition of SEED Ciphersuites to
         Transport Layer Security (TLS)";
  }

  identity tls-dh-dss-with-seed-cbc-sha {
    base cipher-suite-alg-base;
    status deprecated;
    description
      "TLS-DH-DSS-WITH-SEED-CBC-SHA";
    reference
      "RFC 4162:
         Addition of SEED Ciphersuites to
         Transport Layer Security (TLS)";
  }

  identity tls-dh-rsa-with-seed-cbc-sha {
    base cipher-suite-alg-base;
    status deprecated;
    description
      "TLS-DH-RSA-WITH-SEED-CBC-SHA";
    reference
      "RFC 4162:
         Addition of SEED Ciphersuites to
         Transport Layer Security (TLS)";
  }

  identity tls-dhe-dss-with-seed-cbc-sha {
    base cipher-suite-alg-base;
    status deprecated;
    description
      "TLS-DHE-DSS-WITH-SEED-CBC-SHA";
    reference
      "RFC 4162:
         Addition of SEED Ciphersuites to
         Transport Layer Security (TLS)";
  }

  identity tls-dhe-rsa-with-seed-cbc-sha {
    base cipher-suite-alg-base;
    status deprecated;
    description
      "TLS-DHE-RSA-WITH-SEED-CBC-SHA";
    reference
      "RFC 4162:
         Addition of SEED Ciphersuites to
         Transport Layer Security (TLS)";
  }
  identity tls-dh-anon-with-seed-cbc-sha {
    base cipher-suite-alg-base;
    status deprecated;
    description
      "TLS-DH-ANON-WITH-SEED-CBC-SHA";
    reference
      "RFC 4162:
         Addition of SEED Ciphersuites to
         Transport Layer Security (TLS)";
  }

  identity tls-rsa-with-aes-128-gcm-sha256 {
    base cipher-suite-alg-base;
    status deprecated;
    description
      "TLS-RSA-WITH-AES-128-GCM-SHA256";
    reference
      "RFC 5288:
         AES-GCM Cipher Suites for TLS";
  }

  identity tls-rsa-with-aes-256-gcm-sha384 {
    base cipher-suite-alg-base;
    status deprecated;
    description
      "TLS-RSA-WITH-AES-256-GCM-SHA384";
    reference
      "RFC 5288:
         AES-GCM Cipher Suites for TLS";
  }

  identity tls-dhe-rsa-with-aes-128-gcm-sha256 {
    base cipher-suite-alg-base;
    description
      "TLS-DHE-RSA-WITH-AES-128-GCM-SHA256";
    reference
      "RFC 5288:
         AES-GCM Cipher Suites for TLS";
  }

  identity tls-dhe-rsa-with-aes-256-gcm-sha384 {
    base cipher-suite-alg-base;
    description
      "TLS-DHE-RSA-WITH-AES-256-GCM-SHA384";
    reference
      "RFC 5288:
         AES-GCM Cipher Suites for TLS";
  }
  identity tls-dh-rsa-with-aes-128-gcm-sha256 {
    base cipher-suite-alg-base;
    status deprecated;
    description
      "TLS-DH-RSA-WITH-AES-128-GCM-SHA256";
    reference
      "RFC 5288:
         AES-GCM Cipher Suites for TLS";
  }

  identity tls-dh-rsa-with-aes-256-gcm-sha384 {
    base cipher-suite-alg-base;
    status deprecated;
    description
      "TLS-DH-RSA-WITH-AES-256-GCM-SHA384";
    reference
      "RFC 5288:
         AES-GCM Cipher Suites for TLS";
  }

  identity tls-dhe-dss-with-aes-128-gcm-sha256 {
    base cipher-suite-alg-base;
    status deprecated;
    description
      "TLS-DHE-DSS-WITH-AES-128-GCM-SHA256";
    reference
      "RFC 5288:
         AES-GCM Cipher Suites for TLS";
  }

  identity tls-dhe-dss-with-aes-256-gcm-sha384 {
    base cipher-suite-alg-base;
    status deprecated;
    description
      "TLS-DHE-DSS-WITH-AES-256-GCM-SHA384";
    reference
      "RFC 5288:
         AES-GCM Cipher Suites for TLS";
  }

  identity tls-dh-dss-with-aes-128-gcm-sha256 {
    base cipher-suite-alg-base;
    status deprecated;
    description
      "TLS-DH-DSS-WITH-AES-128-GCM-SHA256";
    reference
      "RFC 5288:
         AES-GCM Cipher Suites for TLS";
  }

  identity tls-dh-dss-with-aes-256-gcm-sha384 {
    base cipher-suite-alg-base;
    status deprecated;
    description
      "TLS-DH-DSS-WITH-AES-256-GCM-SHA384";
    reference
      "RFC 5288:
         AES-GCM Cipher Suites for TLS";
  }

  identity tls-dh-anon-with-aes-128-gcm-sha256 {
    base cipher-suite-alg-base;
    status deprecated;
    description
      "TLS-DH-ANON-WITH-AES-128-GCM-SHA256";
    reference
      "RFC 5288:
         AES-GCM Cipher Suites for TLS";
  }

  identity tls-dh-anon-with-aes-256-gcm-sha384 {
    base cipher-suite-alg-base;
    status deprecated;
    description
      "TLS-DH-ANON-WITH-AES-256-GCM-SHA384";
    reference
      "RFC 5288:
         AES-GCM Cipher Suites for TLS";
  }

  identity tls-psk-with-aes-128-gcm-sha256 {
    base cipher-suite-alg-base;
    status deprecated;
    description
      "TLS-PSK-WITH-AES-128-GCM-SHA256";
    reference
      "RFC 5487:
         Pre-Shared Key Cipher Suites for Transport Layer Security
         (TLS) with SHA-256/384 and AES Galois Counter Mode";
  }

  identity tls-psk-with-aes-256-gcm-sha384 {
    base cipher-suite-alg-base;
    status deprecated;
    description
      "TLS-PSK-WITH-AES-256-GCM-SHA384";
    reference
      "RFC 5487:
         Pre-Shared Key Cipher Suites for Transport Layer Security
         (TLS) with SHA-256/384 and AES Galois Counter Mode";
  }

  identity tls-dhe-psk-with-aes-128-gcm-sha256 {
    base cipher-suite-alg-base;
    description
      "TLS-DHE-PSK-WITH-AES-128-GCM-SHA256";
    reference
      "RFC 5487:
         Pre-Shared Key Cipher Suites for Transport Layer Security
         (TLS) with SHA-256/384 and AES Galois Counter Mode";
  }

  identity tls-dhe-psk-with-aes-256-gcm-sha384 {
    base cipher-suite-alg-base;
    description
      "TLS-DHE-PSK-WITH-AES-256-GCM-SHA384";
    reference
      "RFC 5487:
         Pre-Shared Key Cipher Suites for Transport Layer Security
         (TLS) with SHA-256/384 and AES Galois Counter Mode";
  }

  identity tls-rsa-psk-with-aes-128-gcm-sha256 {
    base cipher-suite-alg-base;
    status deprecated;
    description
      "TLS-RSA-PSK-WITH-AES-128-GCM-SHA256";
    reference
      "RFC 5487:
         Pre-Shared Key Cipher Suites for Transport Layer Security
         (TLS) with SHA-256/384 and AES Galois Counter Mode";
  }

  identity tls-rsa-psk-with-aes-256-gcm-sha384 {
    base cipher-suite-alg-base;
    status deprecated;
    description
      "TLS-RSA-PSK-WITH-AES-256-GCM-SHA384";
    reference
      "RFC 5487:
         Pre-Shared Key Cipher Suites for Transport Layer Security
         (TLS) with SHA-256/384 and AES Galois Counter Mode";
  }

  identity tls-psk-with-aes-128-cbc-sha256 {
    base cipher-suite-alg-base;
    status deprecated;
    description
      "TLS-PSK-WITH-AES-128-CBC-SHA256";
    reference
      "RFC 5487:
         Pre-Shared Key Cipher Suites for Transport Layer Security
         (TLS) with SHA-256/384 and AES Galois Counter Mode";
  }

  identity tls-psk-with-aes-256-cbc-sha384 {
    base cipher-suite-alg-base;
    status deprecated;
    description
      "TLS-PSK-WITH-AES-256-CBC-SHA384";
    reference
      "RFC 5487:
         Pre-Shared Key Cipher Suites for Transport Layer Security
         (TLS) with SHA-256/384 and AES Galois Counter Mode";
  }

  identity tls-psk-with-null-sha256 {
    base cipher-suite-alg-base;
    status deprecated;
    description
      "TLS-PSK-WITH-NULL-SHA256";
    reference
      "RFC 5487:
         Pre-Shared Key Cipher Suites for Transport Layer Security
         (TLS) with SHA-256/384 and AES Galois Counter Mode";
  }

  identity tls-psk-with-null-sha384 {
    base cipher-suite-alg-base;
    status deprecated;
    description
      "TLS-PSK-WITH-NULL-SHA384";
    reference
      "RFC 5487:
         Pre-Shared Key Cipher Suites for Transport Layer Security
         (TLS) with SHA-256/384 and AES Galois Counter Mode";
  }

  identity tls-dhe-psk-with-aes-128-cbc-sha256 {
    base cipher-suite-alg-base;
    status deprecated;
    description
      "TLS-DHE-PSK-WITH-AES-128-CBC-SHA256";
    reference
      "RFC 5487:
         Pre-Shared Key Cipher Suites for Transport Layer Security
         (TLS) with SHA-256/384 and AES Galois Counter Mode";
  }

  identity tls-dhe-psk-with-aes-256-cbc-sha384 {
    base cipher-suite-alg-base;
    status deprecated;
    description
      "TLS-DHE-PSK-WITH-AES-256-CBC-SHA384";
    reference
      "RFC 5487:
         Pre-Shared Key Cipher Suites for Transport Layer Security
         (TLS) with SHA-256/384 and AES Galois Counter Mode";
  }

  identity tls-dhe-psk-with-null-sha256 {
    base cipher-suite-alg-base;
    status deprecated;
    description
      "TLS-DHE-PSK-WITH-NULL-SHA256";
    reference
      "RFC 5487:
         Pre-Shared Key Cipher Suites for Transport Layer Security
         (TLS) with SHA-256/384 and AES Galois Counter Mode";
  }

  identity tls-dhe-psk-with-null-sha384 {
    base cipher-suite-alg-base;
    status deprecated;
    description
      "TLS-DHE-PSK-WITH-NULL-SHA384";
    reference
      "RFC 5487:
         Pre-Shared Key Cipher Suites for Transport Layer Security
         (TLS) with SHA-256/384 and AES Galois Counter Mode";
  }

  identity tls-rsa-psk-with-aes-128-cbc-sha256 {
    base cipher-suite-alg-base;
    status deprecated;
    description
      "TLS-RSA-PSK-WITH-AES-128-CBC-SHA256";
    reference
      "RFC 5487:
         Pre-Shared Key Cipher Suites for Transport Layer Security
         (TLS) with SHA-256/384 and AES Galois Counter Mode";
  }

  identity tls-rsa-psk-with-aes-256-cbc-sha384 {
    base cipher-suite-alg-base;
    status deprecated;
    description
      "TLS-RSA-PSK-WITH-AES-256-CBC-SHA384";
    reference
      "RFC 5487:
         Pre-Shared Key Cipher Suites for Transport Layer Security
         (TLS) with SHA-256/384 and AES Galois Counter Mode";
  }

  identity tls-rsa-psk-with-null-sha256 {
    base cipher-suite-alg-base;
    status deprecated;
    description
      "TLS-RSA-PSK-WITH-NULL-SHA256";
    reference
      "RFC 5487:
         Pre-Shared Key Cipher Suites for Transport Layer Security
         (TLS) with SHA-256/384 and AES Galois Counter Mode";
  }

  identity tls-rsa-psk-with-null-sha384 {
    base cipher-suite-alg-base;
    status deprecated;
    description
      "TLS-RSA-PSK-WITH-NULL-SHA384";
    reference
      "RFC 5487:
         Pre-Shared Key Cipher Suites for Transport Layer Security
         (TLS) with SHA-256/384 and AES Galois Counter Mode";
  }

  identity tls-rsa-with-camellia-128-cbc-sha256 {
    base cipher-suite-alg-base;
    status deprecated;
    description
      "TLS-RSA-WITH-CAMELLIA-128-CBC-SHA256";
    reference
      "RFC 5932:
         Camellia Cipher Suites for TLS";
  }

  identity tls-dh-dss-with-camellia-128-cbc-sha256 {
    base cipher-suite-alg-base;
    status deprecated;
    description
      "TLS-DH-DSS-WITH-CAMELLIA-128-CBC-SHA256";
    reference
      "RFC 5932:
         Camellia Cipher Suites for TLS";
  }

  identity tls-dh-rsa-with-camellia-128-cbc-sha256 {
    base cipher-suite-alg-base;
    status deprecated;
    description
      "TLS-DH-RSA-WITH-CAMELLIA-128-CBC-SHA256";
    reference
      "RFC 5932:
         Camellia Cipher Suites for TLS";
  }

  identity tls-dhe-dss-with-camellia-128-cbc-sha256 {
    base cipher-suite-alg-base;
    status deprecated;
    description
      "TLS-DHE-DSS-WITH-CAMELLIA-128-CBC-SHA256";
    reference
      "RFC 5932:
         Camellia Cipher Suites for TLS";
  }

  identity tls-dhe-rsa-with-camellia-128-cbc-sha256 {
    base cipher-suite-alg-base;
    status deprecated;
    description
      "TLS-DHE-RSA-WITH-CAMELLIA-128-CBC-SHA256";
    reference
      "RFC 5932:
         Camellia Cipher Suites for TLS";
  }

  identity tls-dh-anon-with-camellia-128-cbc-sha256 {
    base cipher-suite-alg-base;
    status deprecated;
    description
      "TLS-DH-ANON-WITH-CAMELLIA-128-CBC-SHA256";
    reference
      "RFC 5932:
         Camellia Cipher Suites for TLS";
  }

  identity tls-rsa-with-camellia-256-cbc-sha256 {
    base cipher-suite-alg-base;
    status deprecated;
    description
      "TLS-RSA-WITH-CAMELLIA-256-CBC-SHA256";
    reference
      "RFC 5932:
         Camellia Cipher Suites for TLS";
  }

  identity tls-dh-dss-with-camellia-256-cbc-sha256 {
    base cipher-suite-alg-base;
    status deprecated;
    description
      "TLS-DH-DSS-WITH-CAMELLIA-256-CBC-SHA256";
    reference
      "RFC 5932:
         Camellia Cipher Suites for TLS";
  }

  identity tls-dh-rsa-with-camellia-256-cbc-sha256 {
    base cipher-suite-alg-base;
    status deprecated;
    description
      "TLS-DH-RSA-WITH-CAMELLIA-256-CBC-SHA256";
    reference
      "RFC 5932:
         Camellia Cipher Suites for TLS";
  }

  identity tls-dhe-dss-with-camellia-256-cbc-sha256 {
    base cipher-suite-alg-base;
    status deprecated;
    description
      "TLS-DHE-DSS-WITH-CAMELLIA-256-CBC-SHA256";
    reference
      "RFC 5932:
         Camellia Cipher Suites for TLS";
  }

  identity tls-dhe-rsa-with-camellia-256-cbc-sha256 {
    base cipher-suite-alg-base;
    status deprecated;
    description
      "TLS-DHE-RSA-WITH-CAMELLIA-256-CBC-SHA256";
    reference
      "RFC 5932:
         Camellia Cipher Suites for TLS";
  }

  identity tls-dh-anon-with-camellia-256-cbc-sha256 {
    base cipher-suite-alg-base;
    status deprecated;
    description
      "TLS-DH-ANON-WITH-CAMELLIA-256-CBC-SHA256";
    reference
      "RFC 5932:
         Camellia Cipher Suites for TLS";
  }

  identity tls-sm4-gcm-sm3 {
    base cipher-suite-alg-base;
    status deprecated;
    description
      "TLS-SM4-GCM-SM3";
    reference
      "RFC 8998:
         ShangMi (SM) Cipher Suites for Transport Layer Security
         (TLS) Protocol Version 1.3";
  }

  identity tls-sm4-ccm-sm3 {
    base cipher-suite-alg-base;
    status deprecated;
    description
      "TLS-SM4-CCM-SM3";
    reference
      "RFC 8998:
         ShangMi (SM) Cipher Suites for Transport Layer Security
         (TLS) Protocol Version 1.3";
  }

  identity tls-empty-renegotiation-info-scsv {
    base cipher-suite-alg-base;
    status deprecated;
    description
      "TLS-EMPTY-RENEGOTIATION-INFO-SCSV";
    reference
      "RFC 5746:
         Transport Layer Security (TLS)
         Renegotiation Indication Extension";
  }

  identity tls-aes-128-gcm-sha256 {
    base cipher-suite-alg-base;
    description
      "TLS-AES-128-GCM-SHA256";
    reference
      "RFC 8446:
         The Transport Layer Security (TLS) Protocol Version 1.3";
  }

  identity tls-aes-256-gcm-sha384 {
    base cipher-suite-alg-base;
    description
      "TLS-AES-256-GCM-SHA384";
    reference
      "RFC 8446:
         The Transport Layer Security (TLS) Protocol Version 1.3";
  }

  identity tls-chacha20-poly1305-sha256 {
    base cipher-suite-alg-base;
    description
      "TLS-CHACHA20-POLY1305-SHA256";
    reference
      "RFC 8446:
         The Transport Layer Security (TLS) Protocol Version 1.3";
  }

  identity tls-aes-128-ccm-sha256 {
    base cipher-suite-alg-base;
    description
      "TLS-AES-128-CCM-SHA256";
    reference
      "RFC 8446:
         The Transport Layer Security (TLS) Protocol Version 1.3";
  }

  identity tls-aes-128-ccm-8-sha256 {
    base cipher-suite-alg-base;
    status deprecated;
    description
      "TLS-AES-128-CCM-8-SHA256";
    reference
      "RFC 8446:
         The Transport Layer Security (TLS) Protocol Version 1.3";
  }

  identity tls-fallback-scsv {
    base cipher-suite-alg-base;
    status deprecated;
    description
      "TLS-FALLBACK-SCSV";
    reference
      "RFC 7507:
         TLS Fallback Signaling Cipher Suite Value (SCSV)
         for Preventing Protocol Downgrade Attacks";
  }

  identity tls-ecdh-ecdsa-with-null-sha {
    base cipher-suite-alg-base;
    status deprecated;
    description
      "TLS-ECDH-ECDSA-WITH-NULL-SHA";
    reference
      "RFC 8422:
         Elliptic Curve Cryptography (ECC) Cipher Suites for
         Transport Layer Security (TLS) Versions 1.2 and Earlier";
  }

  identity tls-ecdh-ecdsa-with-rc4-128-sha {
    base cipher-suite-alg-base;
    status deprecated;
    description
      "TLS-ECDH-ECDSA-WITH-RC4-128-SHA";
    reference
      "RFC 8422:
         Elliptic Curve Cryptography (ECC) Cipher Suites for
         Transport Layer Security (TLS) Versions 1.2 and Earlier
       RFC 6347:
         Datagram Transport Layer Security version 1.2";
  }

  identity tls-ecdh-ecdsa-with-3des-ede-cbc-sha {
    base cipher-suite-alg-base;
    status deprecated;
    description
      "TLS-ECDH-ECDSA-WITH-3DES-EDE-CBC-SHA";
    reference
      "RFC 8422:
         Elliptic Curve Cryptography (ECC) Cipher Suites for
         Transport Layer Security (TLS) Versions 1.2 and Earlier";
  }

  identity tls-ecdh-ecdsa-with-aes-128-cbc-sha {
    base cipher-suite-alg-base;
    status deprecated;
    description
      "TLS-ECDH-ECDSA-WITH-AES-128-CBC-SHA";
    reference
      "RFC 8422:
         Elliptic Curve Cryptography (ECC) Cipher Suites for
         Transport Layer Security (TLS) Versions 1.2 and Earlier";
  }

  identity tls-ecdh-ecdsa-with-aes-256-cbc-sha {
    base cipher-suite-alg-base;
    status deprecated;
    description
      "TLS-ECDH-ECDSA-WITH-AES-256-CBC-SHA";
    reference
      "RFC 8422:
         Elliptic Curve Cryptography (ECC) Cipher Suites for
         Transport Layer Security (TLS) Versions 1.2 and Earlier";
  }

  identity tls-ecdhe-ecdsa-with-null-sha {
    base cipher-suite-alg-base;
    status deprecated;
    description
      "TLS-ECDHE-ECDSA-WITH-NULL-SHA";
    reference
      "RFC 8422:
         Elliptic Curve Cryptography (ECC) Cipher Suites for
         Transport Layer Security (TLS) Versions 1.2 and Earlier";
  }

  identity tls-ecdhe-ecdsa-with-rc4-128-sha {
    base cipher-suite-alg-base;
    status deprecated;
    description
      "TLS-ECDHE-ECDSA-WITH-RC4-128-SHA";
    reference
      "RFC 8422:
         Elliptic Curve Cryptography (ECC) Cipher Suites for
         Transport Layer Security (TLS) Versions 1.2 and Earlier
       RFC 6347:
         Datagram Transport Layer Security version 1.2";
  }

  identity tls-ecdhe-ecdsa-with-3des-ede-cbc-sha {
    base cipher-suite-alg-base;
    status deprecated;
    description
      "TLS-ECDHE-ECDSA-WITH-3DES-EDE-CBC-SHA";
    reference
      "RFC 8422:
         Elliptic Curve Cryptography (ECC) Cipher Suites for
         Transport Layer Security (TLS) Versions 1.2 and Earlier";
  }

  identity tls-ecdhe-ecdsa-with-aes-128-cbc-sha {
    base cipher-suite-alg-base;
    status deprecated;
    description
      "TLS-ECDHE-ECDSA-WITH-AES-128-CBC-SHA";
    reference
      "RFC 8422:
         Elliptic Curve Cryptography (ECC) Cipher Suites for
         Transport Layer Security (TLS) Versions 1.2 and Earlier";
  }

  identity tls-ecdhe-ecdsa-with-aes-256-cbc-sha {
    base cipher-suite-alg-base;
    status deprecated;
    description
      "TLS-ECDHE-ECDSA-WITH-AES-256-CBC-SHA";
    reference
      "RFC 8422:
         Elliptic Curve Cryptography (ECC) Cipher Suites for
         Transport Layer Security (TLS) Versions 1.2 and Earlier";
  }

  identity tls-ecdh-rsa-with-null-sha {
    base cipher-suite-alg-base;
    status deprecated;
    description
      "TLS-ECDH-RSA-WITH-NULL-SHA";
    reference
      "RFC 8422:
         Elliptic Curve Cryptography (ECC) Cipher Suites for
         Transport Layer Security (TLS) Versions 1.2 and Earlier";
  }

  identity tls-ecdh-rsa-with-rc4-128-sha {
    base cipher-suite-alg-base;
    status deprecated;
    description
      "TLS-ECDH-RSA-WITH-RC4-128-SHA";
    reference
      "RFC 8422:
         Elliptic Curve Cryptography (ECC) Cipher Suites for
         Transport Layer Security (TLS) Versions 1.2 and Earlier
       RFC 6347:
         Datagram Transport Layer Security version 1.2";
  }

  identity tls-ecdh-rsa-with-3des-ede-cbc-sha {
    base cipher-suite-alg-base;
    status deprecated;
    description
      "TLS-ECDH-RSA-WITH-3DES-EDE-CBC-SHA";
    reference
      "RFC 8422:
         Elliptic Curve Cryptography (ECC) Cipher Suites for
         Transport Layer Security (TLS) Versions 1.2 and Earlier";
  }

  identity tls-ecdh-rsa-with-aes-128-cbc-sha {
    base cipher-suite-alg-base;
    status deprecated;
    description
      "TLS-ECDH-RSA-WITH-AES-128-CBC-SHA";
    reference
      "RFC 8422:
         Elliptic Curve Cryptography (ECC) Cipher Suites for
         Transport Layer Security (TLS) Versions 1.2 and Earlier";
  }

  identity tls-ecdh-rsa-with-aes-256-cbc-sha {
    base cipher-suite-alg-base;
    status deprecated;
    description
      "TLS-ECDH-RSA-WITH-AES-256-CBC-SHA";
    reference
      "RFC 8422:
         Elliptic Curve Cryptography (ECC) Cipher Suites for
         Transport Layer Security (TLS) Versions 1.2 and Earlier";
  }

  identity tls-ecdhe-rsa-with-null-sha {
    base cipher-suite-alg-base;
    status deprecated;
    description
      "TLS-ECDHE-RSA-WITH-NULL-SHA";
    reference
      "RFC 8422:
         Elliptic Curve Cryptography (ECC) Cipher Suites for
         Transport Layer Security (TLS) Versions 1.2 and Earlier";
  }

  identity tls-ecdhe-rsa-with-rc4-128-sha {
    base cipher-suite-alg-base;
    status deprecated;
    description
      "TLS-ECDHE-RSA-WITH-RC4-128-SHA";
    reference
      "RFC 8422:
         Elliptic Curve Cryptography (ECC) Cipher Suites for
         Transport Layer Security (TLS) Versions 1.2 and Earlier
       RFC 6347:
         Datagram Transport Layer Security version 1.2";
  }

  identity tls-ecdhe-rsa-with-3des-ede-cbc-sha {
    base cipher-suite-alg-base;
    status deprecated;
    description
      "TLS-ECDHE-RSA-WITH-3DES-EDE-CBC-SHA";
    reference
      "RFC 8422:
         Elliptic Curve Cryptography (ECC) Cipher Suites for
         Transport Layer Security (TLS) Versions 1.2 and Earlier";
  }

  identity tls-ecdhe-rsa-with-aes-128-cbc-sha {
    base cipher-suite-alg-base;
    status deprecated;
    description
      "TLS-ECDHE-RSA-WITH-AES-128-CBC-SHA";
    reference
      "RFC 8422:
         Elliptic Curve Cryptography (ECC) Cipher Suites for
         Transport Layer Security (TLS) Versions 1.2 and Earlier";
  }

  identity tls-ecdhe-rsa-with-aes-256-cbc-sha {
    base cipher-suite-alg-base;
    status deprecated;
    description
      "TLS-ECDHE-RSA-WITH-AES-256-CBC-SHA";
    reference
      "RFC 8422:
         Elliptic Curve Cryptography (ECC) Cipher Suites for
         Transport Layer Security (TLS) Versions 1.2 and Earlier";
  }

  identity tls-ecdh-anon-with-null-sha {
    base cipher-suite-alg-base;
    status deprecated;
    description
      "TLS-ECDH-ANON-WITH-NULL-SHA";
    reference
      "RFC 8422:
         Elliptic Curve Cryptography (ECC) Cipher Suites for
         Transport Layer Security (TLS) Versions 1.2 and Earlier";
  }

  identity tls-ecdh-anon-with-rc4-128-sha {
    base cipher-suite-alg-base;
    status deprecated;
    description
      "TLS-ECDH-ANON-WITH-RC4-128-SHA";
    reference
      "RFC 8422:
         Elliptic Curve Cryptography (ECC) Cipher Suites for
         Transport Layer Security (TLS) Versions 1.2 and Earlier
       RFC 6347:
         Datagram Transport Layer Security version 1.2";
  }

  identity tls-ecdh-anon-with-3des-ede-cbc-sha {
    base cipher-suite-alg-base;
    status deprecated;
    description
      "TLS-ECDH-ANON-WITH-3DES-EDE-CBC-SHA";
    reference
      "RFC 8422:
         Elliptic Curve Cryptography (ECC) Cipher Suites for
         Transport Layer Security (TLS) Versions 1.2 and Earlier";
  }

  identity tls-ecdh-anon-with-aes-128-cbc-sha {
    base cipher-suite-alg-base;
    status deprecated;
    description
      "TLS-ECDH-ANON-WITH-AES-128-CBC-SHA";
    reference
      "RFC 8422:
         Elliptic Curve Cryptography (ECC) Cipher Suites for
         Transport Layer Security (TLS) Versions 1.2 and Earlier";
  }

  identity tls-ecdh-anon-with-aes-256-cbc-sha {
    base cipher-suite-alg-base;
    status deprecated;
    description
      "TLS-ECDH-ANON-WITH-AES-256-CBC-SHA";
    reference
      "RFC 8422:
         Elliptic Curve Cryptography (ECC) Cipher Suites for
         Transport Layer Security (TLS) Versions 1.2 and Earlier";
  }

  identity tls-srp-sha-with-3des-ede-cbc-sha {
    base cipher-suite-alg-base;
    status deprecated;
    description
      "TLS-SRP-SHA-WITH-3DES-EDE-CBC-SHA";
    reference
      "RFC 5054:
         Using SRP for TLS Authentication";
  }

  identity tls-srp-sha-rsa-with-3des-ede-cbc-sha {
    base cipher-suite-alg-base;
    status deprecated;
    description
      "TLS-SRP-SHA-RSA-WITH-3DES-EDE-CBC-SHA";
    reference
      "RFC 5054:
         Using SRP for TLS Authentication";
  }

  identity tls-srp-sha-dss-with-3des-ede-cbc-sha {
    base cipher-suite-alg-base;
    status deprecated;
    description
      "TLS-SRP-SHA-DSS-WITH-3DES-EDE-CBC-SHA";
    reference
      "RFC 5054:
         Using SRP for TLS Authentication";
  }

  identity tls-srp-sha-with-aes-128-cbc-sha {
    base cipher-suite-alg-base;
    status deprecated;
    description
      "TLS-SRP-SHA-WITH-AES-128-CBC-SHA";
    reference
      "RFC 5054:
         Using SRP for TLS Authentication";
  }

  identity tls-srp-sha-rsa-with-aes-128-cbc-sha {
    base cipher-suite-alg-base;
    status deprecated;
    description
      "TLS-SRP-SHA-RSA-WITH-AES-128-CBC-SHA";
    reference
      "RFC 5054:
         Using SRP for TLS Authentication";
  }

  identity tls-srp-sha-dss-with-aes-128-cbc-sha {
    base cipher-suite-alg-base;
    status deprecated;
    description
      "TLS-SRP-SHA-DSS-WITH-AES-128-CBC-SHA";
    reference
      "RFC 5054:
         Using SRP for TLS Authentication";
  }

  identity tls-srp-sha-with-aes-256-cbc-sha {
    base cipher-suite-alg-base;
    status deprecated;
    description
      "TLS-SRP-SHA-WITH-AES-256-CBC-SHA";
    reference
      "RFC 5054:
         Using SRP for TLS Authentication";
  }

  identity tls-srp-sha-rsa-with-aes-256-cbc-sha {
    base cipher-suite-alg-base;
    status deprecated;
    description
      "TLS-SRP-SHA-RSA-WITH-AES-256-CBC-SHA";
    reference
      "RFC 5054:
         Using SRP for TLS Authentication";
  }

  identity tls-srp-sha-dss-with-aes-256-cbc-sha {
    base cipher-suite-alg-base;
    status deprecated;
    description
      "TLS-SRP-SHA-DSS-WITH-AES-256-CBC-SHA";
    reference
      "RFC 5054:
         Using SRP for TLS Authentication";
  }

  identity tls-ecdhe-ecdsa-with-aes-128-cbc-sha256 {
    base cipher-suite-alg-base;
    status deprecated;
    description
      "TLS-ECDHE-ECDSA-WITH-AES-128-CBC-SHA256";
    reference
      "RFC 5289:
         TLS Elliptic Curve Cipher Suites with SHA-256/384
         and AES Galois Counter Mode";
  }

  identity tls-ecdhe-ecdsa-with-aes-256-cbc-sha384 {
    base cipher-suite-alg-base;
    status deprecated;
    description
      "TLS-ECDHE-ECDSA-WITH-AES-256-CBC-SHA384";
    reference
      "RFC 5289:
         TLS Elliptic Curve Cipher Suites with SHA-256/384
         and AES Galois Counter Mode";
  }

  identity tls-ecdh-ecdsa-with-aes-128-cbc-sha256 {
    base cipher-suite-alg-base;
    status deprecated;
    description
      "TLS-ECDH-ECDSA-WITH-AES-128-CBC-SHA256";
    reference
      "RFC 5289:
         TLS Elliptic Curve Cipher Suites with SHA-256/384
         and AES Galois Counter Mode";
  }

  identity tls-ecdh-ecdsa-with-aes-256-cbc-sha384 {
    base cipher-suite-alg-base;
    status deprecated;
    description
      "TLS-ECDH-ECDSA-WITH-AES-256-CBC-SHA384";
    reference
      "RFC 5289:
         TLS Elliptic Curve Cipher Suites with SHA-256/384
         and AES Galois Counter Mode";
  }

  identity tls-ecdhe-rsa-with-aes-128-cbc-sha256 {
    base cipher-suite-alg-base;
    status deprecated;
    description
      "TLS-ECDHE-RSA-WITH-AES-128-CBC-SHA256";
    reference
      "RFC 5289:
         TLS Elliptic Curve Cipher Suites with SHA-256/384
         and AES Galois Counter Mode";
  }

  identity tls-ecdhe-rsa-with-aes-256-cbc-sha384 {
    base cipher-suite-alg-base;
    status deprecated;
    description
      "TLS-ECDHE-RSA-WITH-AES-256-CBC-SHA384";
    reference
      "RFC 5289:
         TLS Elliptic Curve Cipher Suites with SHA-256/384
         and AES Galois Counter Mode";
  }

  identity tls-ecdh-rsa-with-aes-128-cbc-sha256 {
    base cipher-suite-alg-base;
    status deprecated;
    description
      "TLS-ECDH-RSA-WITH-AES-128-CBC-SHA256";
    reference
      "RFC 5289:
         TLS Elliptic Curve Cipher Suites with SHA-256/384
         and AES Galois Counter Mode";
  }

  identity tls-ecdh-rsa-with-aes-256-cbc-sha384 {
    base cipher-suite-alg-base;
    status deprecated;
    description
      "TLS-ECDH-RSA-WITH-AES-256-CBC-SHA384";
    reference
      "RFC 5289:
         TLS Elliptic Curve Cipher Suites with SHA-256/384
         and AES Galois Counter Mode";
  }

  identity tls-ecdhe-ecdsa-with-aes-128-gcm-sha256 {
    base cipher-suite-alg-base;
    description
      "TLS-ECDHE-ECDSA-WITH-AES-128-GCM-SHA256";
    reference
      "RFC 5289:
         TLS Elliptic Curve Cipher Suites with SHA-256/384
         and AES Galois Counter Mode";
  }

  identity tls-ecdhe-ecdsa-with-aes-256-gcm-sha384 {
    base cipher-suite-alg-base;
    description
      "TLS-ECDHE-ECDSA-WITH-AES-256-GCM-SHA384";
    reference
      "RFC 5289:
         TLS Elliptic Curve Cipher Suites with SHA-256/384
         and AES Galois Counter Mode";
  }

  identity tls-ecdh-ecdsa-with-aes-128-gcm-sha256 {
    base cipher-suite-alg-base;
    status deprecated;
    description
      "TLS-ECDH-ECDSA-WITH-AES-128-GCM-SHA256";
    reference
      "RFC 5289:
         TLS Elliptic Curve Cipher Suites with SHA-256/384
         and AES Galois Counter Mode";
  }

  identity tls-ecdh-ecdsa-with-aes-256-gcm-sha384 {
    base cipher-suite-alg-base;
    status deprecated;
    description
      "TLS-ECDH-ECDSA-WITH-AES-256-GCM-SHA384";
    reference
      "RFC 5289:
         TLS Elliptic Curve Cipher Suites with SHA-256/384
         and AES Galois Counter Mode";
  }

  identity tls-ecdhe-rsa-with-aes-128-gcm-sha256 {
    base cipher-suite-alg-base;
    description
      "TLS-ECDHE-RSA-WITH-AES-128-GCM-SHA256";
    reference
      "RFC 5289:
         TLS Elliptic Curve Cipher Suites with SHA-256/384
         and AES Galois Counter Mode";
  }

  identity tls-ecdhe-rsa-with-aes-256-gcm-sha384 {
    base cipher-suite-alg-base;
    description
      "TLS-ECDHE-RSA-WITH-AES-256-GCM-SHA384";
    reference
      "RFC 5289:
         TLS Elliptic Curve Cipher Suites with SHA-256/384
         and AES Galois Counter Mode";
  }

  identity tls-ecdh-rsa-with-aes-128-gcm-sha256 {
    base cipher-suite-alg-base;
    status deprecated;
    description
      "TLS-ECDH-RSA-WITH-AES-128-GCM-SHA256";
    reference
      "RFC 5289:
         TLS Elliptic Curve Cipher Suites with SHA-256/384
         and AES Galois Counter Mode";
  }

  identity tls-ecdh-rsa-with-aes-256-gcm-sha384 {
    base cipher-suite-alg-base;
    status deprecated;
    description
      "TLS-ECDH-RSA-WITH-AES-256-GCM-SHA384";
    reference
      "RFC 5289:
         TLS Elliptic Curve Cipher Suites with SHA-256/384
         and AES Galois Counter Mode";
  }

  identity tls-ecdhe-psk-with-rc4-128-sha {
    base cipher-suite-alg-base;
    status deprecated;
    description
      "TLS-ECDHE-PSK-WITH-RC4-128-SHA";
    reference
      "RFC 5489:
         ECDHE_PSK Ciphersuites for Transport Layer Security (TLS)
       RFC 6347:
         Datagram Transport Layer Security version 1.2";
  }

  identity tls-ecdhe-psk-with-3des-ede-cbc-sha {
    base cipher-suite-alg-base;
    status deprecated;
    description
      "TLS-ECDHE-PSK-WITH-3DES-EDE-CBC-SHA";
    reference
      "RFC 5489:
         ECDHE_PSK Ciphersuites for Transport Layer Security (TLS)";
  }

  identity tls-ecdhe-psk-with-aes-128-cbc-sha {
    base cipher-suite-alg-base;
    status deprecated;
    description
      "TLS-ECDHE-PSK-WITH-AES-128-CBC-SHA";
    reference
      "RFC 5489:
         ECDHE_PSK Ciphersuites for Transport Layer Security (TLS)";
  }

  identity tls-ecdhe-psk-with-aes-256-cbc-sha {
    base cipher-suite-alg-base;
    status deprecated;
    description
      "TLS-ECDHE-PSK-WITH-AES-256-CBC-SHA";
    reference
      "RFC 5489:
         ECDHE_PSK Ciphersuites for Transport Layer Security (TLS)";
  }

  identity tls-ecdhe-psk-with-aes-128-cbc-sha256 {
    base cipher-suite-alg-base;
    status deprecated;
    description
      "TLS-ECDHE-PSK-WITH-AES-128-CBC-SHA256";
    reference
      "RFC 5489:
         ECDHE_PSK Ciphersuites for Transport Layer Security (TLS)";
  }

  identity tls-ecdhe-psk-with-aes-256-cbc-sha384 {
    base cipher-suite-alg-base;
    status deprecated;
    description
      "TLS-ECDHE-PSK-WITH-AES-256-CBC-SHA384";
    reference
      "RFC 5489:
         ECDHE_PSK Ciphersuites for Transport Layer Security (TLS)";
  }

  identity tls-ecdhe-psk-with-null-sha {
    base cipher-suite-alg-base;
    status deprecated;
    description
      "TLS-ECDHE-PSK-WITH-NULL-SHA";
    reference
      "RFC 5489:
         ECDHE_PSK Ciphersuites for Transport Layer Security (TLS)";
  }
  identity tls-ecdhe-psk-with-null-sha256 {
    base cipher-suite-alg-base;
    status deprecated;
    description
      "TLS-ECDHE-PSK-WITH-NULL-SHA256";
    reference
      "RFC 5489:
         ECDHE_PSK Ciphersuites for Transport Layer Security (TLS)";
  }

  identity tls-ecdhe-psk-with-null-sha384 {
    base cipher-suite-alg-base;
    status deprecated;
    description
      "TLS-ECDHE-PSK-WITH-NULL-SHA384";
    reference
      "RFC 5489:
         ECDHE_PSK Ciphersuites for Transport Layer Security (TLS)";
  }

  identity tls-rsa-with-aria-128-cbc-sha256 {
    base cipher-suite-alg-base;
    status deprecated;
    description
      "TLS-RSA-WITH-ARIA-128-CBC-SHA256";
    reference
      "RFC 6209:
         Addition of the ARIA Cipher Suites to
         Transport Layer Security (TLS)";
  }

  identity tls-rsa-with-aria-256-cbc-sha384 {
    base cipher-suite-alg-base;
    status deprecated;
    description
      "TLS-RSA-WITH-ARIA-256-CBC-SHA384";
    reference
      "RFC 6209:
         Addition of the ARIA Cipher Suites to
         Transport Layer Security (TLS)";
  }

  identity tls-dh-dss-with-aria-128-cbc-sha256 {
    base cipher-suite-alg-base;
    status deprecated;
    description
      "TLS-DH-DSS-WITH-ARIA-128-CBC-SHA256";
    reference
      "RFC 6209:
         Addition of the ARIA Cipher Suites to
         Transport Layer Security (TLS)";
  }

  identity tls-dh-dss-with-aria-256-cbc-sha384 {
    base cipher-suite-alg-base;
    status deprecated;
    description
      "TLS-DH-DSS-WITH-ARIA-256-CBC-SHA384";
    reference
      "RFC 6209:
         Addition of the ARIA Cipher Suites to
         Transport Layer Security (TLS)";
  }

  identity tls-dh-rsa-with-aria-128-cbc-sha256 {
    base cipher-suite-alg-base;
    status deprecated;
    description
      "TLS-DH-RSA-WITH-ARIA-128-CBC-SHA256";
    reference
      "RFC 6209:
         Addition of the ARIA Cipher Suites to
         Transport Layer Security (TLS)";
  }

  identity tls-dh-rsa-with-aria-256-cbc-sha384 {
    base cipher-suite-alg-base;
    status deprecated;
    description
      "TLS-DH-RSA-WITH-ARIA-256-CBC-SHA384";
    reference
      "RFC 6209:
         Addition of the ARIA Cipher Suites to
         Transport Layer Security (TLS)";
  }

  identity tls-dhe-dss-with-aria-128-cbc-sha256 {
    base cipher-suite-alg-base;
    status deprecated;
    description
      "TLS-DHE-DSS-WITH-ARIA-128-CBC-SHA256";
    reference
      "RFC 6209:
         Addition of the ARIA Cipher Suites to
         Transport Layer Security (TLS)";
  }
  identity tls-dhe-dss-with-aria-256-cbc-sha384 {
    base cipher-suite-alg-base;
    status deprecated;
    description
      "TLS-DHE-DSS-WITH-ARIA-256-CBC-SHA384";
    reference
      "RFC 6209:
         Addition of the ARIA Cipher Suites to
         Transport Layer Security (TLS)";
  }

  identity tls-dhe-rsa-with-aria-128-cbc-sha256 {
    base cipher-suite-alg-base;
    status deprecated;
    description
      "TLS-DHE-RSA-WITH-ARIA-128-CBC-SHA256";
    reference
      "RFC 6209:
         Addition of the ARIA Cipher Suites to
         Transport Layer Security (TLS)";
  }

  identity tls-dhe-rsa-with-aria-256-cbc-sha384 {
    base cipher-suite-alg-base;
    status deprecated;
    description
      "TLS-DHE-RSA-WITH-ARIA-256-CBC-SHA384";
    reference
      "RFC 6209:
         Addition of the ARIA Cipher Suites to
         Transport Layer Security (TLS)";
  }

  identity tls-dh-anon-with-aria-128-cbc-sha256 {
    base cipher-suite-alg-base;
    status deprecated;
    description
      "TLS-DH-ANON-WITH-ARIA-128-CBC-SHA256";
    reference
      "RFC 6209:
         Addition of the ARIA Cipher Suites to
         Transport Layer Security (TLS)";
  }

  identity tls-dh-anon-with-aria-256-cbc-sha384 {
    base cipher-suite-alg-base;
    status deprecated;
    description
      "TLS-DH-ANON-WITH-ARIA-256-CBC-SHA384";
    reference
      "RFC 6209:
         Addition of the ARIA Cipher Suites to
         Transport Layer Security (TLS)";
  }

  identity tls-ecdhe-ecdsa-with-aria-128-cbc-sha256 {
    base cipher-suite-alg-base;
    status deprecated;
    description
      "TLS-ECDHE-ECDSA-WITH-ARIA-128-CBC-SHA256";
    reference
      "RFC 6209:
         Addition of the ARIA Cipher Suites to
         Transport Layer Security (TLS)";
  }

  identity tls-ecdhe-ecdsa-with-aria-256-cbc-sha384 {
    base cipher-suite-alg-base;
    status deprecated;
    description
      "TLS-ECDHE-ECDSA-WITH-ARIA-256-CBC-SHA384";
    reference
      "RFC 6209:
         Addition of the ARIA Cipher Suites to
         Transport Layer Security (TLS)";
  }

  identity tls-ecdh-ecdsa-with-aria-128-cbc-sha256 {
    base cipher-suite-alg-base;
    status deprecated;
    description
      "TLS-ECDH-ECDSA-WITH-ARIA-128-CBC-SHA256";
    reference
      "RFC 6209:
         Addition of the ARIA Cipher Suites to
         Transport Layer Security (TLS)";
  }

  identity tls-ecdh-ecdsa-with-aria-256-cbc-sha384 {
    base cipher-suite-alg-base;
    status deprecated;
    description
      "TLS-ECDH-ECDSA-WITH-ARIA-256-CBC-SHA384";
    reference
      "RFC 6209:
         Addition of the ARIA Cipher Suites to
         Transport Layer Security (TLS)";
  }

  identity tls-ecdhe-rsa-with-aria-128-cbc-sha256 {
    base cipher-suite-alg-base;
    status deprecated;
    description
      "TLS-ECDHE-RSA-WITH-ARIA-128-CBC-SHA256";
    reference
      "RFC 6209:
         Addition of the ARIA Cipher Suites to
         Transport Layer Security (TLS)";
  }

  identity tls-ecdhe-rsa-with-aria-256-cbc-sha384 {
    base cipher-suite-alg-base;
    status deprecated;
    description
      "TLS-ECDHE-RSA-WITH-ARIA-256-CBC-SHA384";
    reference
      "RFC 6209:
         Addition of the ARIA Cipher Suites to
         Transport Layer Security (TLS)";
  }

  identity tls-ecdh-rsa-with-aria-128-cbc-sha256 {
    base cipher-suite-alg-base;
    status deprecated;
    description
      "TLS-ECDH-RSA-WITH-ARIA-128-CBC-SHA256";
    reference
      "RFC 6209:
         Addition of the ARIA Cipher Suites to
         Transport Layer Security (TLS)";
  }

  identity tls-ecdh-rsa-with-aria-256-cbc-sha384 {
    base cipher-suite-alg-base;
    status deprecated;
    description
      "TLS-ECDH-RSA-WITH-ARIA-256-CBC-SHA384";
    reference
      "RFC 6209:
         Addition of the ARIA Cipher Suites to
         Transport Layer Security (TLS)";
  }

  identity tls-rsa-with-aria-128-gcm-sha256 {
    base cipher-suite-alg-base;
    status deprecated;
    description
      "TLS-RSA-WITH-ARIA-128-GCM-SHA256";
    reference
      "RFC 6209:
         Addition of the ARIA Cipher Suites to
         Transport Layer Security (TLS)";
  }

  identity tls-rsa-with-aria-256-gcm-sha384 {
    base cipher-suite-alg-base;
    status deprecated;
    description
      "TLS-RSA-WITH-ARIA-256-GCM-SHA384";
    reference
      "RFC 6209:
         Addition of the ARIA Cipher Suites to
         Transport Layer Security (TLS)";
  }

  identity tls-dhe-rsa-with-aria-128-gcm-sha256 {
    base cipher-suite-alg-base;
    status deprecated;
    description
      "TLS-DHE-RSA-WITH-ARIA-128-GCM-SHA256";
    reference
      "RFC 6209:
         Addition of the ARIA Cipher Suites to
         Transport Layer Security (TLS)";
  }

  identity tls-dhe-rsa-with-aria-256-gcm-sha384 {
    base cipher-suite-alg-base;
    status deprecated;
    description
      "TLS-DHE-RSA-WITH-ARIA-256-GCM-SHA384";
    reference
      "RFC 6209:
         Addition of the ARIA Cipher Suites to
         Transport Layer Security (TLS)";
  }

  identity tls-dh-rsa-with-aria-128-gcm-sha256 {
    base cipher-suite-alg-base;
    status deprecated;
    description
      "TLS-DH-RSA-WITH-ARIA-128-GCM-SHA256";
    reference
      "RFC 6209:
         Addition of the ARIA Cipher Suites to
         Transport Layer Security (TLS)";
  }

  identity tls-dh-rsa-with-aria-256-gcm-sha384 {
    base cipher-suite-alg-base;
    status deprecated;
    description
      "TLS-DH-RSA-WITH-ARIA-256-GCM-SHA384";
    reference
      "RFC 6209:
         Addition of the ARIA Cipher Suites to
         Transport Layer Security (TLS)";
  }

  identity tls-dhe-dss-with-aria-128-gcm-sha256 {
    base cipher-suite-alg-base;
    status deprecated;
    description
      "TLS-DHE-DSS-WITH-ARIA-128-GCM-SHA256";
    reference
      "RFC 6209:
         Addition of the ARIA Cipher Suites to
         Transport Layer Security (TLS)";
  }

  identity tls-dhe-dss-with-aria-256-gcm-sha384 {
    base cipher-suite-alg-base;
    status deprecated;
    description
      "TLS-DHE-DSS-WITH-ARIA-256-GCM-SHA384";
    reference
      "RFC 6209:
         Addition of the ARIA Cipher Suites to
         Transport Layer Security (TLS)";
  }

  identity tls-dh-dss-with-aria-128-gcm-sha256 {
    base cipher-suite-alg-base;
    status deprecated;
    description
      "TLS-DH-DSS-WITH-ARIA-128-GCM-SHA256";
    reference
      "RFC 6209:
         Addition of the ARIA Cipher Suites to
         Transport Layer Security (TLS)";
  }

  identity tls-dh-dss-with-aria-256-gcm-sha384 {
    base cipher-suite-alg-base;
    status deprecated;
    description
      "TLS-DH-DSS-WITH-ARIA-256-GCM-SHA384";
    reference
      "RFC 6209:
         Addition of the ARIA Cipher Suites to
         Transport Layer Security (TLS)";
  }

  identity tls-dh-anon-with-aria-128-gcm-sha256 {
    base cipher-suite-alg-base;
    status deprecated;
    description
      "TLS-DH-ANON-WITH-ARIA-128-GCM-SHA256";
    reference
      "RFC 6209:
         Addition of the ARIA Cipher Suites to
         Transport Layer Security (TLS)";
  }

  identity tls-dh-anon-with-aria-256-gcm-sha384 {
    base cipher-suite-alg-base;
    status deprecated;
    description
      "TLS-DH-ANON-WITH-ARIA-256-GCM-SHA384";
    reference
      "RFC 6209:
         Addition of the ARIA Cipher Suites to
         Transport Layer Security (TLS)";
  }

  identity tls-ecdhe-ecdsa-with-aria-128-gcm-sha256 {
    base cipher-suite-alg-base;
    status deprecated;
    description
      "TLS-ECDHE-ECDSA-WITH-ARIA-128-GCM-SHA256";
    reference
      "RFC 6209:
         Addition of the ARIA Cipher Suites to
         Transport Layer Security (TLS)";
  }

  identity tls-ecdhe-ecdsa-with-aria-256-gcm-sha384 {
    base cipher-suite-alg-base;
    status deprecated;
    description
      "TLS-ECDHE-ECDSA-WITH-ARIA-256-GCM-SHA384";
    reference
      "RFC 6209:
         Addition of the ARIA Cipher Suites to
         Transport Layer Security (TLS)";
  }

  identity tls-ecdh-ecdsa-with-aria-128-gcm-sha256 {
    base cipher-suite-alg-base;
    status deprecated;
    description
      "TLS-ECDH-ECDSA-WITH-ARIA-128-GCM-SHA256";
    reference
      "RFC 6209:
         Addition of the ARIA Cipher Suites to
         Transport Layer Security (TLS)";
  }

  identity tls-ecdh-ecdsa-with-aria-256-gcm-sha384 {
    base cipher-suite-alg-base;
    status deprecated;
    description
      "TLS-ECDH-ECDSA-WITH-ARIA-256-GCM-SHA384";
    reference
      "RFC 6209:
         Addition of the ARIA Cipher Suites to
         Transport Layer Security (TLS)";
  }

  identity tls-ecdhe-rsa-with-aria-128-gcm-sha256 {
    base cipher-suite-alg-base;
    status deprecated;
    description
      "TLS-ECDHE-RSA-WITH-ARIA-128-GCM-SHA256";
    reference
      "RFC 6209:
         Addition of the ARIA Cipher Suites to
         Transport Layer Security (TLS)";
  }

  identity tls-ecdhe-rsa-with-aria-256-gcm-sha384 {
    base cipher-suite-alg-base;
    status deprecated;
    description
      "TLS-ECDHE-RSA-WITH-ARIA-256-GCM-SHA384";
    reference
      "RFC 6209:
         Addition of the ARIA Cipher Suites to
         Transport Layer Security (TLS)";
  }

  identity tls-ecdh-rsa-with-aria-128-gcm-sha256 {
    base cipher-suite-alg-base;
    status deprecated;
    description
      "TLS-ECDH-RSA-WITH-ARIA-128-GCM-SHA256";
    reference
      "RFC 6209:
         Addition of the ARIA Cipher Suites to
         Transport Layer Security (TLS)";
  }

  identity tls-ecdh-rsa-with-aria-256-gcm-sha384 {
    base cipher-suite-alg-base;
    status deprecated;
    description
      "TLS-ECDH-RSA-WITH-ARIA-256-GCM-SHA384";
    reference
      "RFC 6209:
         Addition of the ARIA Cipher Suites to
         Transport Layer Security (TLS)";
  }

  identity tls-psk-with-aria-128-cbc-sha256 {
    base cipher-suite-alg-base;
    status deprecated;
    description
      "TLS-PSK-WITH-ARIA-128-CBC-SHA256";
    reference
      "RFC 6209:
         Addition of the ARIA Cipher Suites to
         Transport Layer Security (TLS)";
  }

  identity tls-psk-with-aria-256-cbc-sha384 {
    base cipher-suite-alg-base;
    status deprecated;
    description
      "TLS-PSK-WITH-ARIA-256-CBC-SHA384";
    reference
      "RFC 6209:
         Addition of the ARIA Cipher Suites to
         Transport Layer Security (TLS)";
  }
  identity tls-dhe-psk-with-aria-128-cbc-sha256 {
    base cipher-suite-alg-base;
    status deprecated;
    description
      "TLS-DHE-PSK-WITH-ARIA-128-CBC-SHA256";
    reference
      "RFC 6209:
         Addition of the ARIA Cipher Suites to
         Transport Layer Security (TLS)";
  }

  identity tls-dhe-psk-with-aria-256-cbc-sha384 {
    base cipher-suite-alg-base;
    status deprecated;
    description
      "TLS-DHE-PSK-WITH-ARIA-256-CBC-SHA384";
    reference
      "RFC 6209:
         Addition of the ARIA Cipher Suites to
         Transport Layer Security (TLS)";
  }

  identity tls-rsa-psk-with-aria-128-cbc-sha256 {
    base cipher-suite-alg-base;
    status deprecated;
    description
      "TLS-RSA-PSK-WITH-ARIA-128-CBC-SHA256";
    reference
      "RFC 6209:
         Addition of the ARIA Cipher Suites to
         Transport Layer Security (TLS)";
  }

  identity tls-rsa-psk-with-aria-256-cbc-sha384 {
    base cipher-suite-alg-base;
    status deprecated;
    description
      "TLS-RSA-PSK-WITH-ARIA-256-CBC-SHA384";
    reference
      "RFC 6209:
         Addition of the ARIA Cipher Suites to
         Transport Layer Security (TLS)";
  }

  identity tls-psk-with-aria-128-gcm-sha256 {
    base cipher-suite-alg-base;
    status deprecated;
    description
      "TLS-PSK-WITH-ARIA-128-GCM-SHA256";
    reference
      "RFC 6209:
         Addition of the ARIA Cipher Suites to
         Transport Layer Security (TLS)";
  }

  identity tls-psk-with-aria-256-gcm-sha384 {
    base cipher-suite-alg-base;
    status deprecated;
    description
      "TLS-PSK-WITH-ARIA-256-GCM-SHA384";
    reference
      "RFC 6209:
         Addition of the ARIA Cipher Suites to
         Transport Layer Security (TLS)";
  }

  identity tls-dhe-psk-with-aria-128-gcm-sha256 {
    base cipher-suite-alg-base;
    status deprecated;
    description
      "TLS-DHE-PSK-WITH-ARIA-128-GCM-SHA256";
    reference
      "RFC 6209:
         Addition of the ARIA Cipher Suites to
         Transport Layer Security (TLS)";
  }

  identity tls-dhe-psk-with-aria-256-gcm-sha384 {
    base cipher-suite-alg-base;
    status deprecated;
    description
      "TLS-DHE-PSK-WITH-ARIA-256-GCM-SHA384";
    reference
      "RFC 6209:
         Addition of the ARIA Cipher Suites to
         Transport Layer Security (TLS)";
  }

  identity tls-rsa-psk-with-aria-128-gcm-sha256 {
    base cipher-suite-alg-base;
    status deprecated;
    description
      "TLS-RSA-PSK-WITH-ARIA-128-GCM-SHA256";
    reference
      "RFC 6209:
         Addition of the ARIA Cipher Suites to
         Transport Layer Security (TLS)";
  }

  identity tls-rsa-psk-with-aria-256-gcm-sha384 {
    base cipher-suite-alg-base;
    status deprecated;
    description
      "TLS-RSA-PSK-WITH-ARIA-256-GCM-SHA384";
    reference
      "RFC 6209:
         Addition of the ARIA Cipher Suites to
         Transport Layer Security (TLS)";
  }

  identity tls-ecdhe-psk-with-aria-128-cbc-sha256 {
    base cipher-suite-alg-base;
    status deprecated;
    description
      "TLS-ECDHE-PSK-WITH-ARIA-128-CBC-SHA256";
    reference
      "RFC 6209:
         Addition of the ARIA Cipher Suites to
         Transport Layer Security (TLS)";
  }

  identity tls-ecdhe-psk-with-aria-256-cbc-sha384 {
    base cipher-suite-alg-base;
    status deprecated;
    description
      "TLS-ECDHE-PSK-WITH-ARIA-256-CBC-SHA384";
    reference
      "RFC 6209:
         Addition of the ARIA Cipher Suites to
         Transport Layer Security (TLS)";
  }

  identity tls-ecdhe-ecdsa-with-camellia-128-cbc-sha256 {
    base cipher-suite-alg-base;
    status deprecated;
    description
      "TLS-ECDHE-ECDSA-WITH-CAMELLIA-128-CBC-SHA256";
    reference
      "RFC 6367:
         Addition of the Camellia Cipher Suites to
         Transport Layer Security (TLS)";
  }

  identity tls-ecdhe-ecdsa-with-camellia-256-cbc-sha384 {
    base cipher-suite-alg-base;
    status deprecated;
    description
      "TLS-ECDHE-ECDSA-WITH-CAMELLIA-256-CBC-SHA384";
    reference
      "RFC 6367:
         Addition of the Camellia Cipher Suites to
         Transport Layer Security (TLS)";
  }

  identity tls-ecdh-ecdsa-with-camellia-128-cbc-sha256 {
    base cipher-suite-alg-base;
    status deprecated;
    description
      "TLS-ECDH-ECDSA-WITH-CAMELLIA-128-CBC-SHA256";
    reference
      "RFC 6367:
         Addition of the Camellia Cipher Suites to
         Transport Layer Security (TLS)";
  }

  identity tls-ecdh-ecdsa-with-camellia-256-cbc-sha384 {
    base cipher-suite-alg-base;
    status deprecated;
    description
      "TLS-ECDH-ECDSA-WITH-CAMELLIA-256-CBC-SHA384";
    reference
      "RFC 6367:
         Addition of the Camellia Cipher Suites to
         Transport Layer Security (TLS)";
  }

  identity tls-ecdhe-rsa-with-camellia-128-cbc-sha256 {
    base cipher-suite-alg-base;
    status deprecated;
    description
      "TLS-ECDHE-RSA-WITH-CAMELLIA-128-CBC-SHA256";
    reference
      "RFC 6367:
         Addition of the Camellia Cipher Suites to
         Transport Layer Security (TLS)";
  }

  identity tls-ecdhe-rsa-with-camellia-256-cbc-sha384 {
    base cipher-suite-alg-base;
    status deprecated;
    description
      "TLS-ECDHE-RSA-WITH-CAMELLIA-256-CBC-SHA384";
    reference
      "RFC 6367:
         Addition of the Camellia Cipher Suites to
         Transport Layer Security (TLS)";
  }

  identity tls-ecdh-rsa-with-camellia-128-cbc-sha256 {
    base cipher-suite-alg-base;
    status deprecated;
    description
      "TLS-ECDH-RSA-WITH-CAMELLIA-128-CBC-SHA256";
    reference
      "RFC 6367:
         Addition of the Camellia Cipher Suites to
         Transport Layer Security (TLS)";
  }

  identity tls-ecdh-rsa-with-camellia-256-cbc-sha384 {
    base cipher-suite-alg-base;
    status deprecated;
    description
      "TLS-ECDH-RSA-WITH-CAMELLIA-256-CBC-SHA384";
    reference
      "RFC 6367:
         Addition of the Camellia Cipher Suites to
         Transport Layer Security (TLS)";
  }

  identity tls-rsa-with-camellia-128-gcm-sha256 {
    base cipher-suite-alg-base;
    status deprecated;
    description
      "TLS-RSA-WITH-CAMELLIA-128-GCM-SHA256";
    reference
      "RFC 6367:
         Addition of the Camellia Cipher Suites to
         Transport Layer Security (TLS)";
  }

  identity tls-rsa-with-camellia-256-gcm-sha384 {
    base cipher-suite-alg-base;
    status deprecated;
    description
      "TLS-RSA-WITH-CAMELLIA-256-GCM-SHA384";
    reference
      "RFC 6367:
         Addition of the Camellia Cipher Suites to
         Transport Layer Security (TLS)";
  }

  identity tls-dhe-rsa-with-camellia-128-gcm-sha256 {
    base cipher-suite-alg-base;
    status deprecated;
    description
      "TLS-DHE-RSA-WITH-CAMELLIA-128-GCM-SHA256";
    reference
      "RFC 6367:
         Addition of the Camellia Cipher Suites to
         Transport Layer Security (TLS)";
  }

  identity tls-dhe-rsa-with-camellia-256-gcm-sha384 {
    base cipher-suite-alg-base;
    status deprecated;
    description
      "TLS-DHE-RSA-WITH-CAMELLIA-256-GCM-SHA384";
    reference
      "RFC 6367:
         Addition of the Camellia Cipher Suites to
         Transport Layer Security (TLS)";
  }

  identity tls-dh-rsa-with-camellia-128-gcm-sha256 {
    base cipher-suite-alg-base;
    status deprecated;
    description
      "TLS-DH-RSA-WITH-CAMELLIA-128-GCM-SHA256";
    reference
      "RFC 6367:
         Addition of the Camellia Cipher Suites to
         Transport Layer Security (TLS)";
  }

  identity tls-dh-rsa-with-camellia-256-gcm-sha384 {
    base cipher-suite-alg-base;
    status deprecated;
    description
      "TLS-DH-RSA-WITH-CAMELLIA-256-GCM-SHA384";
    reference
      "RFC 6367:
         Addition of the Camellia Cipher Suites to
         Transport Layer Security (TLS)";
  }

  identity tls-dhe-dss-with-camellia-128-gcm-sha256 {
    base cipher-suite-alg-base;
    status deprecated;
    description
      "TLS-DHE-DSS-WITH-CAMELLIA-128-GCM-SHA256";
    reference
      "RFC 6367:
         Addition of the Camellia Cipher Suites to
         Transport Layer Security (TLS)";
  }

  identity tls-dhe-dss-with-camellia-256-gcm-sha384 {
    base cipher-suite-alg-base;
    status deprecated;
    description
      "TLS-DHE-DSS-WITH-CAMELLIA-256-GCM-SHA384";
    reference
      "RFC 6367:
         Addition of the Camellia Cipher Suites to
         Transport Layer Security (TLS)";
  }

  identity tls-dh-dss-with-camellia-128-gcm-sha256 {
    base cipher-suite-alg-base;
    status deprecated;
    description
      "TLS-DH-DSS-WITH-CAMELLIA-128-GCM-SHA256";
    reference
      "RFC 6367:
         Addition of the Camellia Cipher Suites to
         Transport Layer Security (TLS)";
  }

  identity tls-dh-dss-with-camellia-256-gcm-sha384 {
    base cipher-suite-alg-base;
    status deprecated;
    description
      "TLS-DH-DSS-WITH-CAMELLIA-256-GCM-SHA384";
    reference
      "RFC 6367:
         Addition of the Camellia Cipher Suites to
         Transport Layer Security (TLS)";
  }

  identity tls-dh-anon-with-camellia-128-gcm-sha256 {
    base cipher-suite-alg-base;
    status deprecated;
    description
      "TLS-DH-ANON-WITH-CAMELLIA-128-GCM-SHA256";
    reference
      "RFC 6367:
         Addition of the Camellia Cipher Suites to
         Transport Layer Security (TLS)";
  }

  identity tls-dh-anon-with-camellia-256-gcm-sha384 {
    base cipher-suite-alg-base;
    status deprecated;
    description
      "TLS-DH-ANON-WITH-CAMELLIA-256-GCM-SHA384";
    reference
      "RFC 6367:
         Addition of the Camellia Cipher Suites to
         Transport Layer Security (TLS)";
  }

  identity tls-ecdhe-ecdsa-with-camellia-128-gcm-sha256 {
    base cipher-suite-alg-base;
    status deprecated;
    description
      "TLS-ECDHE-ECDSA-WITH-CAMELLIA-128-GCM-SHA256";
    reference
      "RFC 6367:
         Addition of the Camellia Cipher Suites to
         Transport Layer Security (TLS)";
  }

  identity tls-ecdhe-ecdsa-with-camellia-256-gcm-sha384 {
    base cipher-suite-alg-base;
    status deprecated;
    description
      "TLS-ECDHE-ECDSA-WITH-CAMELLIA-256-GCM-SHA384";
    reference
      "RFC 6367:
         Addition of the Camellia Cipher Suites to
         Transport Layer Security (TLS)";
  }

  identity tls-ecdh-ecdsa-with-camellia-128-gcm-sha256 {
    base cipher-suite-alg-base;
    status deprecated;
    description
      "TLS-ECDH-ECDSA-WITH-CAMELLIA-128-GCM-SHA256";
    reference
      "RFC 6367:
         Addition of the Camellia Cipher Suites to
         Transport Layer Security (TLS)";
  }
  identity tls-ecdh-ecdsa-with-camellia-256-gcm-sha384 {
    base cipher-suite-alg-base;
    status deprecated;
    description
      "TLS-ECDH-ECDSA-WITH-CAMELLIA-256-GCM-SHA384";
    reference
      "RFC 6367:
         Addition of the Camellia Cipher Suites to
         Transport Layer Security (TLS)";
  }

  identity tls-ecdhe-rsa-with-camellia-128-gcm-sha256 {
    base cipher-suite-alg-base;
    status deprecated;
    description
      "TLS-ECDHE-RSA-WITH-CAMELLIA-128-GCM-SHA256";
    reference
      "RFC 6367:
         Addition of the Camellia Cipher Suites to
         Transport Layer Security (TLS)";
  }

  identity tls-ecdhe-rsa-with-camellia-256-gcm-sha384 {
    base cipher-suite-alg-base;
    status deprecated;
    description
      "TLS-ECDHE-RSA-WITH-CAMELLIA-256-GCM-SHA384";
    reference
      "RFC 6367:
         Addition of the Camellia Cipher Suites to
         Transport Layer Security (TLS)";
  }

  identity tls-ecdh-rsa-with-camellia-128-gcm-sha256 {
    base cipher-suite-alg-base;
    status deprecated;
    description
      "TLS-ECDH-RSA-WITH-CAMELLIA-128-GCM-SHA256";
    reference
      "RFC 6367:
         Addition of the Camellia Cipher Suites to
         Transport Layer Security (TLS)";
  }

  identity tls-ecdh-rsa-with-camellia-256-gcm-sha384 {
    base cipher-suite-alg-base;
    status deprecated;
    description
      "TLS-ECDH-RSA-WITH-CAMELLIA-256-GCM-SHA384";
    reference
      "RFC 6367:
         Addition of the Camellia Cipher Suites to
         Transport Layer Security (TLS)";
  }

  identity tls-psk-with-camellia-128-gcm-sha256 {
    base cipher-suite-alg-base;
    status deprecated;
    description
      "TLS-PSK-WITH-CAMELLIA-128-GCM-SHA256";
    reference
      "RFC 6367:
         Addition of the Camellia Cipher Suites to
         Transport Layer Security (TLS)";
  }

  identity tls-psk-with-camellia-256-gcm-sha384 {
    base cipher-suite-alg-base;
    status deprecated;
    description
      "TLS-PSK-WITH-CAMELLIA-256-GCM-SHA384";
    reference
      "RFC 6367:
         Addition of the Camellia Cipher Suites to
         Transport Layer Security (TLS)";
  }

  identity tls-dhe-psk-with-camellia-128-gcm-sha256 {
    base cipher-suite-alg-base;
    status deprecated;
    description
      "TLS-DHE-PSK-WITH-CAMELLIA-128-GCM-SHA256";
    reference
      "RFC 6367:
         Addition of the Camellia Cipher Suites to
         Transport Layer Security (TLS)";
  }

  identity tls-dhe-psk-with-camellia-256-gcm-sha384 {
    base cipher-suite-alg-base;
    status deprecated;
    description
      "TLS-DHE-PSK-WITH-CAMELLIA-256-GCM-SHA384";
    reference
      "RFC 6367:
         Addition of the Camellia Cipher Suites to
         Transport Layer Security (TLS)";
  }

  identity tls-rsa-psk-with-camellia-128-gcm-sha256 {
    base cipher-suite-alg-base;
    status deprecated;
    description
      "TLS-RSA-PSK-WITH-CAMELLIA-128-GCM-SHA256";
    reference
      "RFC 6367:
         Addition of the Camellia Cipher Suites to
         Transport Layer Security (TLS)";
  }

  identity tls-rsa-psk-with-camellia-256-gcm-sha384 {
    base cipher-suite-alg-base;
    status deprecated;
    description
      "TLS-RSA-PSK-WITH-CAMELLIA-256-GCM-SHA384";
    reference
      "RFC 6367:
         Addition of the Camellia Cipher Suites to
         Transport Layer Security (TLS)";
  }

  identity tls-psk-with-camellia-128-cbc-sha256 {
    base cipher-suite-alg-base;
    status deprecated;
    description
      "TLS-PSK-WITH-CAMELLIA-128-CBC-SHA256";
    reference
      "RFC 6367:
         Addition of the Camellia Cipher Suites to
         Transport Layer Security (TLS)";
  }

  identity tls-psk-with-camellia-256-cbc-sha384 {
    base cipher-suite-alg-base;
    status deprecated;
    description
      "TLS-PSK-WITH-CAMELLIA-256-CBC-SHA384";
    reference
      "RFC 6367:
         Addition of the Camellia Cipher Suites to
         Transport Layer Security (TLS)";
  }

  identity tls-dhe-psk-with-camellia-128-cbc-sha256 {
    base cipher-suite-alg-base;
    status deprecated;
    description
      "TLS-DHE-PSK-WITH-CAMELLIA-128-CBC-SHA256";
    reference
      "RFC 6367:
         Addition of the Camellia Cipher Suites to
         Transport Layer Security (TLS)";
  }

  identity tls-dhe-psk-with-camellia-256-cbc-sha384 {
    base cipher-suite-alg-base;
    status deprecated;
    description
      "TLS-DHE-PSK-WITH-CAMELLIA-256-CBC-SHA384";
    reference
      "RFC 6367:
         Addition of the Camellia Cipher Suites to
         Transport Layer Security (TLS)";
  }

  identity tls-rsa-psk-with-camellia-128-cbc-sha256 {
    base cipher-suite-alg-base;
    status deprecated;
    description
      "TLS-RSA-PSK-WITH-CAMELLIA-128-CBC-SHA256";
    reference
      "RFC 6367:
         Addition of the Camellia Cipher Suites to
         Transport Layer Security (TLS)";
  }

  identity tls-rsa-psk-with-camellia-256-cbc-sha384 {
    base cipher-suite-alg-base;
    status deprecated;
    description
      "TLS-RSA-PSK-WITH-CAMELLIA-256-CBC-SHA384";
    reference
      "RFC 6367:
         Addition of the Camellia Cipher Suites to
         Transport Layer Security (TLS)";
  }

  identity tls-ecdhe-psk-with-camellia-128-cbc-sha256 {
    base cipher-suite-alg-base;
    status deprecated;
    description
      "TLS-ECDHE-PSK-WITH-CAMELLIA-128-CBC-SHA256";
    reference
      "RFC 6367:
         Addition of the Camellia Cipher Suites to
         Transport Layer Security (TLS)";
  }

  identity tls-ecdhe-psk-with-camellia-256-cbc-sha384 {
    base cipher-suite-alg-base;
    status deprecated;
    description
      "TLS-ECDHE-PSK-WITH-CAMELLIA-256-CBC-SHA384";
    reference
      "RFC 6367:
         Addition of the Camellia Cipher Suites to
         Transport Layer Security (TLS)";
  }

  identity tls-rsa-with-aes-128-ccm {
    base cipher-suite-alg-base;
    status deprecated;
    description
      "TLS-RSA-WITH-AES-128-CCM";
    reference
      "RFC 6655:
         AES-CCM Cipher Suites for TLS";
  }

  identity tls-rsa-with-aes-256-ccm {
    base cipher-suite-alg-base;
    status deprecated;
    description
      "TLS-RSA-WITH-AES-256-CCM";
    reference
      "RFC 6655:
         AES-CCM Cipher Suites for TLS";
  }

  identity tls-dhe-rsa-with-aes-128-ccm {
    base cipher-suite-alg-base;
    description
      "TLS-DHE-RSA-WITH-AES-128-CCM";
    reference
      "RFC 6655:
         AES-CCM Cipher Suites for TLS";
  }

  identity tls-dhe-rsa-with-aes-256-ccm {
    base cipher-suite-alg-base;
    description
      "TLS-DHE-RSA-WITH-AES-256-CCM";
    reference
      "RFC 6655:
         AES-CCM Cipher Suites for TLS";
  }

  identity tls-rsa-with-aes-128-ccm-8 {
    base cipher-suite-alg-base;
    status deprecated;
    description
      "TLS-RSA-WITH-AES-128-CCM-8";
    reference
      "RFC 6655:
         AES-CCM Cipher Suites for TLS";
  }

  identity tls-rsa-with-aes-256-ccm-8 {
    base cipher-suite-alg-base;
    status deprecated;
    description
      "TLS-RSA-WITH-AES-256-CCM-8";
    reference
      "RFC 6655:
         AES-CCM Cipher Suites for TLS";
  }

  identity tls-dhe-rsa-with-aes-128-ccm-8 {
    base cipher-suite-alg-base;
    status deprecated;
    description
      "TLS-DHE-RSA-WITH-AES-128-CCM-8";
    reference
      "RFC 6655:
         AES-CCM Cipher Suites for TLS";
  }

  identity tls-dhe-rsa-with-aes-256-ccm-8 {
    base cipher-suite-alg-base;
    status deprecated;
    description
      "TLS-DHE-RSA-WITH-AES-256-CCM-8";
    reference
      "RFC 6655:
         AES-CCM Cipher Suites for TLS";
  }

  identity tls-psk-with-aes-128-ccm {
    base cipher-suite-alg-base;
    status deprecated;
    description
      "TLS-PSK-WITH-AES-128-CCM";
    reference
      "RFC 6655:
         AES-CCM Cipher Suites for TLS";
  }

  identity tls-psk-with-aes-256-ccm {
    base cipher-suite-alg-base;
    status deprecated;
    description
      "TLS-PSK-WITH-AES-256-CCM";
    reference
      "RFC 6655:
         AES-CCM Cipher Suites for TLS";
  }

  identity tls-dhe-psk-with-aes-128-ccm {
    base cipher-suite-alg-base;
    description
      "TLS-DHE-PSK-WITH-AES-128-CCM";
    reference
      "RFC 6655:
         AES-CCM Cipher Suites for TLS";
  }

  identity tls-dhe-psk-with-aes-256-ccm {
    base cipher-suite-alg-base;
    description
      "TLS-DHE-PSK-WITH-AES-256-CCM";
    reference
      "RFC 6655:
         AES-CCM Cipher Suites for TLS";
  }

  identity tls-psk-with-aes-128-ccm-8 {
    base cipher-suite-alg-base;
    status deprecated;
    description
      "TLS-PSK-WITH-AES-128-CCM-8";
    reference
      "RFC 6655:
         AES-CCM Cipher Suites for TLS";
  }

  identity tls-psk-with-aes-256-ccm-8 {
    base cipher-suite-alg-base;
    status deprecated;
    description
      "TLS-PSK-WITH-AES-256-CCM-8";
    reference
      "RFC 6655:
         AES-CCM Cipher Suites for TLS";
  }

  identity tls-psk-dhe-with-aes-128-ccm-8 {
    base cipher-suite-alg-base;
    status deprecated;
    description
      "TLS-PSK-DHE-WITH-AES-128-CCM-8";
    reference
      "RFC 6655:
         AES-CCM Cipher Suites for TLS";
  }

  identity tls-psk-dhe-with-aes-256-ccm-8 {
    base cipher-suite-alg-base;
    status deprecated;
    description
      "TLS-PSK-DHE-WITH-AES-256-CCM-8";
    reference
      "RFC 6655:
         AES-CCM Cipher Suites for TLS";
  }

  identity tls-ecdhe-ecdsa-with-aes-128-ccm {
    base cipher-suite-alg-base;
    status deprecated;
    description
      "TLS-ECDHE-ECDSA-WITH-AES-128-CCM";
    reference
      "RFC 7251:
         AES-CCM ECC Cipher Suites for TLS";
  }

  identity tls-ecdhe-ecdsa-with-aes-256-ccm {
    base cipher-suite-alg-base;
    status deprecated;
    description
      "TLS-ECDHE-ECDSA-WITH-AES-256-CCM";
    reference
      "RFC 7251:
         AES-CCM ECC Cipher Suites for TLS";
  }
  identity tls-ecdhe-ecdsa-with-aes-128-ccm-8 {
    base cipher-suite-alg-base;
    status deprecated;
    description
      "TLS-ECDHE-ECDSA-WITH-AES-128-CCM-8";
    reference
      "RFC 7251:
         AES-CCM ECC Cipher Suites for TLS";
  }

  identity tls-ecdhe-ecdsa-with-aes-256-ccm-8 {
    base cipher-suite-alg-base;
    status deprecated;
    description
      "TLS-ECDHE-ECDSA-WITH-AES-256-CCM-8";
    reference
      "RFC 7251:
         AES-CCM ECC Cipher Suites for TLS";
  }

  identity tls-eccpwd-with-aes-128-gcm-sha256 {
    base cipher-suite-alg-base;
    status deprecated;
    description
      "TLS-ECCPWD-WITH-AES-128-GCM-SHA256";
    reference
      "RFC 8492:
         Secure Password Ciphersuites for
         Transport Layer Security (TLS)";
  }

  identity tls-eccpwd-with-aes-256-gcm-sha384 {
    base cipher-suite-alg-base;
    status deprecated;
    description
      "TLS-ECCPWD-WITH-AES-256-GCM-SHA384";
    reference
      "RFC 8492:
         Secure Password Ciphersuites for
         Transport Layer Security (TLS)";
  }

  identity tls-eccpwd-with-aes-128-ccm-sha256 {
    base cipher-suite-alg-base;
    status deprecated;
    description
      "TLS-ECCPWD-WITH-AES-128-CCM-SHA256";
    reference
      "RFC 8492:
         Secure Password Ciphersuites for
         Transport Layer Security (TLS)";
  }

  identity tls-eccpwd-with-aes-256-ccm-sha384 {
    base cipher-suite-alg-base;
    status deprecated;
    description
      "TLS-ECCPWD-WITH-AES-256-CCM-SHA384";
    reference
      "RFC 8492:
         Secure Password Ciphersuites for
         Transport Layer Security (TLS)";
  }

  identity tls-sha256-sha256 {
    base cipher-suite-alg-base;
    status deprecated;
    description
      "TLS-SHA256-SHA256";
    reference
      "RFC 9150:
         TLS 1.3 Authentication and Integrity-Only Cipher Suites";
  }

  identity tls-sha384-sha384 {
    base cipher-suite-alg-base;
    status deprecated;
    description
      "TLS-SHA384-SHA384";
    reference
      "RFC 9150:
         TLS 1.3 Authentication and Integrity-Only Cipher Suites";
  }

  identity tls-gostr341112-256-with-kuznyechik-ctr-omac {
    base cipher-suite-alg-base;
    status deprecated;
    description
      "TLS-GOSTR341112-256-WITH-KUZNYECHIK-CTR-OMAC";
    reference
      "RFC 9189:
         GOST Cipher Suites for Transport Layer Security (TLS)
         Protocol Version 1.2";
  }

  identity tls-gostr341112-256-with-magma-ctr-omac {
    base cipher-suite-alg-base;
    status deprecated;
    description
      "TLS-GOSTR341112-256-WITH-MAGMA-CTR-OMAC";
    reference
      "RFC 9189:
         GOST Cipher Suites for Transport Layer Security (TLS)
         Protocol Version 1.2";
  }

  identity tls-gostr341112-256-with-28147-cnt-imit {
    base cipher-suite-alg-base;
    status deprecated;
    description
      "TLS-GOSTR341112-256-WITH-28147-CNT-IMIT";
    reference
      "RFC 9189:
         GOST Cipher Suites for Transport Layer Security (TLS)
         Protocol Version 1.2";
  }

  identity tls-ecdhe-rsa-with-chacha20-poly1305-sha256 {
    base cipher-suite-alg-base;
    description
      "TLS-ECDHE-RSA-WITH-CHACHA20-POLY1305-SHA256";
    reference
      "RFC 7905:
         ChaCha20-Poly1305 Cipher Suites for
         Transport Layer Security (TLS)";
  }

  identity tls-ecdhe-ecdsa-with-chacha20-poly1305-sha256 {
    base cipher-suite-alg-base;
    description
      "TLS-ECDHE-ECDSA-WITH-CHACHA20-POLY1305-SHA256";
    reference
      "RFC 7905:
         ChaCha20-Poly1305 Cipher Suites for
         Transport Layer Security (TLS)";
  }

  identity tls-dhe-rsa-with-chacha20-poly1305-sha256 {
    base cipher-suite-alg-base;
    description
      "TLS-DHE-RSA-WITH-CHACHA20-POLY1305-SHA256";
    reference
      "RFC 7905:
         ChaCha20-Poly1305 Cipher Suites for
         Transport Layer Security (TLS)";
  }

  identity tls-psk-with-chacha20-poly1305-sha256 {
    base cipher-suite-alg-base;
    status deprecated;
    description
      "TLS-PSK-WITH-CHACHA20-POLY1305-SHA256";
    reference
      "RFC 7905:
         ChaCha20-Poly1305 Cipher Suites for
         Transport Layer Security (TLS)";
  }

  identity tls-ecdhe-psk-with-chacha20-poly1305-sha256 {
    base cipher-suite-alg-base;
    description
      "TLS-ECDHE-PSK-WITH-CHACHA20-POLY1305-SHA256";
    reference
      "RFC 7905:
         ChaCha20-Poly1305 Cipher Suites for
         Transport Layer Security (TLS)";
  }

  identity tls-dhe-psk-with-chacha20-poly1305-sha256 {
    base cipher-suite-alg-base;
    description
      "TLS-DHE-PSK-WITH-CHACHA20-POLY1305-SHA256";
    reference
      "RFC 7905:
         ChaCha20-Poly1305 Cipher Suites for
         Transport Layer Security (TLS)";
  }

  identity tls-rsa-psk-with-chacha20-poly1305-sha256 {
    base cipher-suite-alg-base;
    status deprecated;
    description
      "TLS-RSA-PSK-WITH-CHACHA20-POLY1305-SHA256";
    reference
      "RFC 7905:
         ChaCha20-Poly1305 Cipher Suites for
         Transport Layer Security (TLS)";
  }

  identity tls-ecdhe-psk-with-aes-128-gcm-sha256 {
    base cipher-suite-alg-base;
    description
      "TLS-ECDHE-PSK-WITH-AES-128-GCM-SHA256";
    reference
      "RFC 8442:
         ECDHE_PSK with AES-GCM and AES-CCM Cipher Suites";
  }

  identity tls-ecdhe-psk-with-aes-256-gcm-sha384 {
    base cipher-suite-alg-base;
    description
      "TLS-ECDHE-PSK-WITH-AES-256-GCM-SHA384";
    reference
      "RFC 8442:
         ECDHE_PSK with AES-GCM and AES-CCM Cipher Suites";
  }

  identity tls-ecdhe-psk-with-aes-128-ccm-8-sha256 {
    base cipher-suite-alg-base;
    status deprecated;
    description
      "TLS-ECDHE-PSK-WITH-AES-128-CCM-8-SHA256";
    reference
      "RFC 8442:
         ECDHE_PSK with AES-GCM and AES-CCM Cipher Suites";
  }

  identity tls-ecdhe-psk-with-aes-128-ccm-sha256 {
    base cipher-suite-alg-base;
    description
      "TLS-ECDHE-PSK-WITH-AES-128-CCM-SHA256";
    reference
      "RFC 8442:
         ECDHE_PSK with AES-GCM and AES-CCM Cipher Suites";
  }

}
