module openconfig-interfaces {
  yang-version "1";
  namespace "http://openconfig.net/yang/interfaces";
  prefix "oc-if";

  container interfaces {
    list interface {
      key "name";
      leaf name { type string; }
      container state {
        config false;
        leaf name { type string; }
        leaf type { type string; }
        leaf admin-status { type string; }
        leaf oper-status { type string; }
        container counters {
          leaf in-octets { type uint64; }
          leaf in-unicast-pkts { type uint64; }
          leaf out-octets { type uint64; }
          leaf out-unicast-pkts { type uint64; }
        }
      }
    }
  }
}
