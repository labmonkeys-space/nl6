module test-dev {
  yang-version 1.1;
  namespace "urn:test:dev";
  prefix td;
  import test-a { prefix ta; }
  revision 2026-01-03 { description "test"; }
  deviation /ta:interfaces/ta:interface/ta:state/ta:removed-by-deviation { deviate not-supported; }
}
